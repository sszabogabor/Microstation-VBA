Attribute VB_Name = "C_ILoc"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False

Implements ILocateCommandEvents

Private m_oStartElement As Element
Private m_tStartPoint As Point3d

'  Both the Dynamics and the Accept event handlers use this
'  method to create a copy of the element and move as far
'  as the cursor has moved.
Function ReadElement(oBase As Element, tInputPoint As Point3d, bAddToModel As Boolean) As Element
    'Dim tDistance As Point3d
    'Dim oContext As New CopyContext

    'With tDistance
    '    .X = tInputPoint.X - m_tStartPoint.X
    '    .Y = tInputPoint.Y - m_tStartPoint.Y
    '    .Z = tInputPoint.Z - m_tStartPoint.Z
    'End With
        Set oSelected_whata = oBase
            Dim whataelement As MsdElementType
            whataelement = oSelected_whata.Type
            'On Error GoTo errorhandler
            
            If whataelement = msdElementTypeText Then
                Dim oSelected As TextElement
                Set oSelected = oBase
                ID = oSelected.ID.Low
                cislo = CDbl(oSelected.Text)
                UserForm1.Label1 = cislo
                
                Call UserForm1.calculation
                
            ElseIf whataelement = msdElementTypeTextNode Then
                Dim oSelectedTLE As TextNodeElement
                Set oSelectedTLE = oBase
                ID = oSelectedTLE.ID.Low
                cislo = CDbl(oSelectedTLE.TextLine(1))
                UserForm1.Label1 = cislo
                Call UserForm1.calculation
                
            ElseIf whataelement = msdElementTypeDimension Then
                Dim oSelectedDIM As DimensionElement
                Set oSelectedDIM = oBase
                ID = oSelectedDIM.ID.Low
                If UserForm1.CheckBox1 = False Then
                    cislo = CDbl(oSelectedDIM.ActualValue)
                    UserForm1.Label1 = Round(cislo * CDbl(UserForm1.TextBox1.Text), CInt(UserForm1.TextBox2.Text))
                Else
                    For i = 1 To oSelectedDIM.SegmentsCount
                    cislo = cislo + CDbl(oSelectedDIM.ActualValue(i))
                    Next i
                    UserForm1.Label1 = Round(cislo * CDbl(UserForm1.TextBox1.Text), CInt(UserForm1.TextBox2.Text))
                End If
                Call UserForm1.calculation
                
            ElseIf whataelement = msdElementTypeCellHeader Then
                    Dim oCellHeader As CellElement
                    Set oCellHeader = oSelected_whata
                    Set ee = oCellHeader.GetSubElements
                        Dim eleComponent As Element
                        Do While (ee.MoveNext)
                            Set eleComponent = ee.Current
                                If eleComponent.Type = msdElementTypeText Then
                                    Dim oSelected1 As TextElement
                                    Set oSelected1 = ee.Current
                                    cislo = CDbl(oSelected1.Text)
                                    UserForm1.Label1 = cislo
                                ElseIf eleComponent.Type = msdElementTypeTextNode Then
                                    Dim oTNE1 As TextNodeElement
                                    Set oTNE1 = eleComponent
                                    'Set oSelectedTLE = oEnumerator.Current
                                    'ID = oSelectedTLE.ID.Low
                                    cislo = CDbl(oTNE1.TextLine(1))
                                    UserForm1.Label1 = cislo
                                    
''                                    Set ee1 = oTNE.GetSubElements
''                                            Do While (ee1.MoveNext)
''                                                Dim oSelected2 As TextElement
''                                                Set oSelected2 = ee1.Current
''                                                cislo = CDbl(oSelected2.Text)
''                                                UserForm1.Label1 = cislo
''                                            Loop
                                
                                End If
                        Loop
                Call UserForm1.calculation
            End If
errorhandler:
    'oContext.AddElementToModel = bAddToModel
    '  CopyElement's default behavior is to add the element to the model. Use
    '  the CopyContext to control whether or not it adds the element to the model.
    'Set CreateMovedElement = ActiveModelReference.CopyElement(m_oStartElement, oContext)
    'CreateMovedElement.Move tDistance
    
End Function


' This is called when the user enters a data point after the
'  LocateFilter has accepted an element
Private Sub ILocateCommandEvents_Accept(ByVal Element As Element, _
                Point As Point3d, ByVal View As View)
    Dim oTemp As Element
    Set oTemp = ReadElement(m_oStartElement, Point, True)

    'oTemp.Rewrite
    'oTemp.Redraw
    CommandState.StartLocate New C_ILoc
End Sub

Private Sub ILocateCommandEvents_Cleanup()

End Sub

Private Sub ILocateCommandEvents_Dynamics(Point As Point3d, _
        ByVal View As View, ByVal DrawMode As MsdDrawingMode)
    'Dim oTemp As Element

    'Set oTemp = ReadElement(m_oStartElement, Point, False)
    'oTemp.Redraw DrawMode
End Sub

Private Sub ILocateCommandEvents_LocateFailed()
    CommandState.StartLocate New C_ILoc
End Sub


Private Sub ILocateCommandEvents_LocateFilter(ByVal Element As Element, _
        Point As Point3d, Accepted As Boolean)
    ' If this method does not set Accepted to False, then
    ' the element is accepted. This functions remembers what
    ' element was accepted and the datapoint used to accept
    ' the element.  Then it starts dynamics.
    Set m_oStartElement = Element
    'm_tStartPoint = Point
    CommandState.StartDynamics
End Sub

Private Sub ILocateCommandEvents_LocateReset()
    
    UserForm1.CommandButton4.Enabled = True
        Dim MyDataObj As New DataObject
        MyDataObj.SetText UserForm1.Label4
        MyDataObj.PutInClipboard
    UserForm1.CommandButton3.Caption = UserForm1.Label4
End Sub

Private Sub ILocateCommandEvents_Start()
    Dim lc As LocateCriteria
    
    '  Since this command does not modify the original element,
    '  set the locate criteria to allow read-only elements.
    Set lc = CommandState.CreateLocateCriteria(False)
    CommandState.SetLocateCriteria lc
    UserForm1.CommandButton4.Enabled = False
    
    '  MicroStation disables AccuSnap whenever a new command starts, so a command
    '  should enable AccuSnap whenever it is appropriate.  This user still has the
    '  ability to turn off AccuSnap. Enabling AccuSnap does not override that.
    '  EnableAccuSnap only enables AccuSnap if the user has it turned on.
    'CommandState.EnableAccuSnap
    
    'ShowCommand "Copy Element"
    ShowPrompt "Select element to add to calc"
    UserForm1.CommandButton3.Caption = "Ctrl+C(Result)"
End Sub

Attribute VB_Name = "Module1"
Sub start_smartcalc()
   
    UserForm1.Show
    'On Error GoTo finish
    '
'finish:
    'MsgBox "Fatal error!"
    'End
End Sub


''''''''''''''
'Szabo Gabor '08

Sub whataelement()



    Dim oEnumerator As ElementEnumerator
        Dim oSelected As Element
        
        
        Set oEnumerator = ActiveModelReference.GetSelectedElements
        
        Do While (oEnumerator.MoveNext)
           
            Set oSelected = oEnumerator.Current
            Dim oType As MsdElementType
            oType = oSelected.Type
            
                Loop

End Sub

Attribute VB_Name = "UserForm1"
Attribute VB_Base = "0{AC07F9E6-5033-4DF3-A449-9BCDE17DF598}{BF0BBF45-8B5D-412E-9D16-17EE1B9713DD}"
Attribute VB_GlobalNameSpace = False
Attribute VB_Creatable = False
Attribute VB_PredeclaredId = True
Attribute VB_Exposed = False
Attribute VB_TemplateDerived = False
Attribute VB_Customizable = False

Private Sub CommandButton1_Click()
        
        Dim cislo As Double
        Dim oEnumerator As ElementEnumerator
        Set oEnumerator = ActiveModelReference.GetSelectedElements
        Dim oSelected_whata As Element
        
        Do While (oEnumerator.MoveNext)
            Set oSelected_whata = oEnumerator.Current
            Dim whataelement As MsdElementType
            whataelement = oSelected_whata.Type
            On Error GoTo errorhandler
            
            If whataelement = msdElementTypeText Then
                Dim oSelected As TextElement
                Set oSelected = oEnumerator.Current
                cislo = CDbl(oSelected.Text)
                UserForm1.Label1 = cislo
                Call calculation
            ElseIf whataelement = msdElementTypeTextNode Then
                Dim oSelectedTLE As TextNodeElement
                Set oSelectedTLE = oEnumerator.Current
                cislo = CDbl(oSelectedTLE.TextLine(1))
                UserForm1.Label1 = cislo
                Call calculation
            ElseIf whataelement = msdElementTypeDimension Then
                Dim oSelectedDIM As DimensionElement
                Set oSelectedDIM = oEnumerator.Current
                If Me.CheckBox1 = False Then
                    cislo = CDbl(oSelectedDIM.ActualValue)
                    UserForm1.Label1 = Round(cislo * CDbl(Me.TextBox1.Text), CInt(Me.TextBox2.Text))
                Else
                    For i = 1 To oSelectedDIM.SegmentsCount
                    cislo = cislo + CDbl(oSelectedDIM.ActualValue(i))
                    Next i
                    UserForm1.Label1 = Round(cislo * CDbl(Me.TextBox1.Text), CInt(Me.TextBox2.Text))
                End If
                Call calculation
            ElseIf whataelement = msdElementTypeCellHeader Then
                    Dim oCellHeader As CellElement
                    Set oCellHeader = oSelected_whata
                    Set ee = oCellHeader.GetSubElements
                        Dim eleComponent As Element
                        Do While (ee.MoveNext)
                            Set eleComponent = ee.Current
                                If eleComponent.Type = msdElementTypeText Then
                                    Dim oSelected1 As TextElement
                                    Set oSelected1 = ee.Current
                                    cislo = CDbl(oSelected1.Text)
                                    UserForm1.Label1 = cislo
                                ElseIf eleComponent.Type = msdElementTypeTextNode Then
                                    Dim oTNE1 As TextNodeElement
                                    Set oTNE1 = eleComponent
                                    'Set oSelectedTLE = oEnumerator.Current
                                    'ID = oSelectedTLE.ID.Low
                                    cislo = CDbl(oTNE1.TextLine(1))
                                    UserForm1.Label1 = cislo
                                    
''                                    Set ee1 = oTNE.GetSubElements
''                                            Do While (ee1.MoveNext)
''                                                Dim oSelected2 As TextElement
''                                                Set oSelected2 = ee1.Current
''                                                cislo = CDbl(oSelected2.Text)
''                                                UserForm1.Label1 = cislo
''                                            Loop
                                
                                End If
                        Loop
                Call calculation
            
            End If
                
            
        
errorhandler:
            ShowStatus "Value: " & cislo
        Loop
        

    'ShowStatus "Updated element number " & "i"
    

End Sub
Sub calculation()
            If UserForm1.OptionButton1 Then
                UserForm1.Label4 = CDbl(UserForm1.Label4) + CDbl(UserForm1.Label1)
                ElseIf UserForm1.OptionButton2 Then
            UserForm1.Label4 = CDbl(UserForm1.Label4) - CDbl(UserForm1.Label1)
                ElseIf UserForm1.OptionButton3 Then
            UserForm1.Label4 = CDbl(UserForm1.Label4) * CDbl(UserForm1.Label1)
                ElseIf UserForm1.OptionButton4 Then
            UserForm1.Label4 = CDbl(UserForm1.Label4) / CDbl(UserForm1.Label1)
            End If
End Sub
Private Sub CommandButton2_Click()
    UserForm1.Label1 = 0
    UserForm1.Label4 = 0
    UserForm1.CommandButton3.Caption = "Ctrl+C(Result)"
    UserForm1.CommandButton4.Enabled = True
End Sub

Private Sub CommandButton3_Click()
    'CtrlC
    Dim MyDataObj As New DataObject
    MyDataObj.SetText Me.Label4
    MyDataObj.PutInClipboard
    
End Sub


Private Sub CommandButton4_Click()
    CommandState.StartLocate New C_ILoc
End Sub
