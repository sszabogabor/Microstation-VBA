Attribute VB_Name = "Module1"
Sub start_smartcalc()
   
    UserForm1.Show
    'On Error GoTo finish
    '
'finish:
    'MsgBox "Fatal error!"
    'End
End Sub


''''''''''''''
'Szabo Gabor '08

Sub whataelement()



    Dim oEnumerator As ElementEnumerator
        Dim oSelected As Element
        
        
        Set oEnumerator = ActiveModelReference.GetSelectedElements
        
        Do While (oEnumerator.MoveNext)
           
            Set oSelected = oEnumerator.Current
            Dim oType As MsdElementType
            oType = oSelected.Type
            
                Loop

End Sub

Attribute VB_Name = "UserForm1"
Attribute VB_Base = "0{093FCD86-6C60-42DA-9C57-695B1789EAEF}{FC098782-74BD-4C3B-9E0C-AD3699D5C0CF}"
Attribute VB_GlobalNameSpace = False
Attribute VB_Creatable = False
Attribute VB_PredeclaredId = True
Attribute VB_Exposed = False
Attribute VB_TemplateDerived = False
Attribute VB_Customizable = False

Private Sub CommandButton1_Click()
        
        Dim cislo As Double
        Dim oEnumerator As ElementEnumerator
        Set oEnumerator = ActiveModelReference.GetSelectedElements
        Dim oSelected_whata As Element
        
        Do While (oEnumerator.MoveNext)
            Set oSelected_whata = oEnumerator.Current
            Dim whataelement As MsdElementType
            whataelement = oSelected_whata.Type
            On Error GoTo errorhandler
            
            If whataelement = msdElementTypeText Then
                Dim oSelected As TextElement
                Set oSelected = oEnumerator.Current
                ID = oSelected.ID.Low
                cislo = CDbl(oSelected.Text)
                UserForm1.Label1 = cislo
                
                Call calculation
            ElseIf whataelement = msdElementTypeTextNode Then
                Dim oSelectedTLE As TextNodeElement
                Set oSelectedTLE = oEnumerator.Current
                ID = oSelectedTLE.ID.Low
                cislo = CDbl(oSelectedTLE.TextLine(1))
                UserForm1.Label1 = cislo
                Call calculation
                
            ElseIf whataelement = msdElementTypeDimension Then
                Dim oSelectedDIM As DimensionElement
                Set oSelectedDIM = oEnumerator.Current
                ID = oSelectedDIM.ID.Low
                cislo = CDbl(oSelectedDIM.ActualValue)
                UserForm1.Label1 = Round(cislo * CDbl(Me.TextBox1.Text), CInt(Me.TextBox2.Text))
                Call calculation
            End If
        
errorhandler:
            ShowStatus "Value: " & cislo
        Loop
        

    'ShowStatus "Updated element number " & "i"
    

End Sub
Sub calculation()
            If UserForm1.OptionButton1 Then
                UserForm1.Label4 = CDbl(UserForm1.Label4) + CDbl(UserForm1.Label1)
                ElseIf UserForm1.OptionButton2 Then
            UserForm1.Label4 = CDbl(UserForm1.Label4) - CDbl(UserForm1.Label1)
                ElseIf UserForm1.OptionButton3 Then
            UserForm1.Label4 = CDbl(UserForm1.Label4) * CDbl(UserForm1.Label1)
                ElseIf UserForm1.OptionButton4 Then
            UserForm1.Label4 = CDbl(UserForm1.Label4) / CDbl(UserForm1.Label1)
            End If
End Sub
Private Sub CommandButton2_Click()
    UserForm1.Label1 = 0
    UserForm1.Label4 = 0
End Sub

Private Sub CommandButton3_Click()
    
    Dim MyDataObj As New DataObject
    MyDataObj.SetText Me.Label4
    MyDataObj.PutInClipboard
    
End Sub
