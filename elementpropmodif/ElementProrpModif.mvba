Attribute VB_Name = "Module1"
Sub start_epm()
   
    UserForm1.Show
    'On Error GoTo finish
    '
'finish:
    'MsgBox "Fatal error!"
    'End
       
    
End Sub

Sub whataelement()



    Dim oEnumerator As ElementEnumerator
        Dim oSelected As Element
        
        
        Set oEnumerator = ActiveModelReference.GetSelectedElements
        
        Do While (oEnumerator.MoveNext)
           
            Set oSelected = oEnumerator.Current
            Dim oType As MsdElementType
            oType = oSelected.Type
            
        Loop

End Sub

Attribute VB_Name = "UserForm1"
Attribute VB_Base = "0{9E1A050B-C449-412F-80A0-27216DAEE3DC}{4BA48EA1-DED7-4665-A5C6-BDD291DFC46C}"
Attribute VB_GlobalNameSpace = False
Attribute VB_Creatable = False
Attribute VB_PredeclaredId = True
Attribute VB_Exposed = False
Attribute VB_TemplateDerived = False
Attribute VB_Customizable = False

Private Sub CommandButton1_Click()
        
        
        Dim oEnumerator As ElementEnumerator
        Set oEnumerator = ActiveModelReference.GetSelectedElements

        
        Do While (oEnumerator.MoveNext)
            Set oSelected_whata = oEnumerator.Current
            Dim whataelement As MsdElementType
            whataelement = oSelected_whata.Type
            Me.Label4 = oSelected_whata.Type
            'On Error GoTo errorhandler
            
            Select Case (whataelement)
                Case 15
                    Me.Label4 = "EllipseElement"
                    Dim oSelected As EllipseElement
                    Set oSelected = oEnumerator.Current
                    ID = oSelected.ID.Low
                    Me.Label1.Visible = True
                    Me.Label2.Visible = True
                    Me.CheckBox1.Visible = True
                    Me.TextBox1.Visible = True
                    Me.TextBox2.Visible = True
                    Me.CheckBox1.Caption = "Circle"
                    Me.Label1 = "PrimaryRadius"
                    Me.Label2 = "SecondaryRadius"
                    Me.TextBox1 = oSelected.PrimaryRadius
                    Me.TextBox2 = oSelected.SecondaryRadius
                    Me.CommandButton2.Enabled = True
                Case 33
                    Me.Label4 = "DimensionElement"
                    Dim oselectedDIM As DimensionElement 'msdElementTypeDimension
                    'Dim oSelectedDIM As msdElementTypeDimension
                    Set oselectedDIM = oEnumerator.Current
                    ID = oselectedDIM.ID.Low
                    Me.Label1.Visible = True
                    Me.Label2.Visible = True
                    Me.CheckBox1.Visible = True
                    Me.TextBox1.Visible = True
                    Me.TextBox2.Visible = True
                    Me.TextBox2.Enabled = True
                    Me.CheckBox1.Caption = "Change for all segment"
                    Me.Label1 = "Value (or last segment value)"
                    Me.Label2 = "New value"
                    'Me.TextBox1 = oSelectedDIM.ActualValue
                    Me.TextBox1 = oselectedDIM.PrimaryText
                    Me.TextBox2 = Empty
                    Me.CommandButton2.Enabled = True
                    Me.CheckBox1.Value = False
                    
                Case 7
                    Me.Label4 = "TextNodeElement"
                    Dim oSelectedTNE As TextNodeElement
                    Set oSelectedTNE = oEnumerator.Current
                    ID = oSelectedTNE.ID.Low
                    Me.Label1.Visible = True
                    Me.Label2.Visible = False
                    Me.CheckBox1.Visible = False
                    Me.TextBox1.Visible = True
                    Me.TextBox2.Visible = False
                    
                    Me.TextBox1 = Empty
                    Me.CommandButton2.Enabled = True
                    Me.Label1 = "Rotation angle in rad"
                   
                    
                
                Case 17
                    Me.Label4 = "TextElement"
                    Dim oSelectedT As TextElement
                    Set oSelectedT = oEnumerator.Current
                    ID = oSelectedT.ID.Low
                    Me.Label1.Visible = True
                    Me.Label2.Visible = False
                    Me.CheckBox1.Visible = False
                    Me.TextBox1.Visible = True
                    Me.TextBox2.Visible = False
                    
                    Me.TextBox1 = Empty
                    Me.CommandButton2.Enabled = True
                    Me.Label1 = "Rotation angle in rad"

      
                Case 3
                    Me.Label4 = "LineElement"
                    Dim oSelectedL As LineElement
                    Set oSelectedL = oEnumerator.Current
                    ID = oSelectedL.ID.Low
                    Me.Label1.Visible = False
                    Me.Label2.Visible = False
                    Me.CheckBox1.Visible = False
                    Me.TextBox1.Visible = False
                    Me.TextBox2.Visible = False
                   
                    'Me.Label1 = "Rotation"
                    'a = oSelectedT.Rotation
                    'Me.TextBox2 = oSelectedT.Rotation.RowY.Y
                     Me.CommandButton2.Enabled = False
                  
                Case Else
                    Me.Label1.Visible = False
                    Me.Label2.Visible = False
                    Me.CheckBox1.Visible = False
                    Me.TextBox1.Visible = False
                    Me.TextBox2.Visible = False
                   
                    'Me.Label1 = "Rotation"
                    'a = oSelectedT.Rotation
                    'Me.TextBox2 = oSelectedT.Rotation.RowY.Y
                     Me.CommandButton2.Enabled = False
                    
                    
            End Select
        
errorhandler:
            'nenechame se vycukat
        Loop

End Sub

Private Sub CommandButton2_Click()
    Dim oEnumerator As ElementEnumerator
    Dim a As Double
        Set oEnumerator = ActiveModelReference.GetSelectedElements

        
        Do While (oEnumerator.MoveNext)
            Set oSelected_whata = oEnumerator.Current
            Dim whataelement As MsdElementType
            whataelement = oSelected_whata.Type
            On Error GoTo errorhandler
            
            Select Case whataelement
                Case 15
                    Dim oSelected As EllipseElement
                    Set oSelected = oEnumerator.Current
                    ID = oSelected.ID.Low
                    If Me.CheckBox1 Then
                        oSelected.PrimaryRadius = CDbl(Replace((Me.TextBox1), ".", ","))
                        oSelected.SecondaryRadius = CDbl(Replace((Me.TextBox1), ".", ","))
                        oSelected.Rewrite
                        oSelected.Redraw
                    Else
                        oSelected.PrimaryRadius = CDbl(Replace((Me.TextBox1), ".", ","))
                        oSelected.SecondaryRadius = CDbl(Replace((Me.TextBox2), ".", ","))
                        oSelected.Rewrite
                        oSelected.Redraw
                    End If
                Case 33
                    Dim oselectedDIM As DimensionElement
                    Set oselectedDIM = oEnumerator.Current
                    If Me.CheckBox1 Then
                        
                        For i = 1 To oselectedDIM.SegmentsCount
                            oselectedDIM.PrimaryText(i) = UserForm1.TextBox2.Value
                            oselectedDIM.Rewrite
                            oselectedDIM.Redraw
                        Next i
                    Else
                        oselectedDIM.PrimaryText = UserForm1.TextBox2.Value
                        oselectedDIM.Rewrite
                        oselectedDIM.Redraw
                    End If
                Case 17
                    Dim oSelectedT As TextElement
                    Set oSelectedT = oEnumerator.Current
                    Angle = Radians(CDbl(Replace(Me.TextBox1.Value, ".", ",")))
                    oSelectedT.RotateAboutZ oSelectedT.Origin, Angle
                    oSelectedT.Rewrite
                    oSelectedT.Redraw
                Case 7
                
                    Dim oSelectedTNE As TextNodeElement
                    Set oSelectedTNE = oEnumerator.Current
                    Angle = Radians(CDbl(Replace(Me.TextBox1.Value, ".", ",")))
                    oSelectedTNE.RotateAboutZ oSelectedTNE.Origin, Angle
                    oSelectedTNE.Rewrite
                    oSelectedTNE.Redraw

            
            End Select
        
errorhandler:
            'nenechame se vycukat
        Loop
End Sub

Private Sub CheckBox1_Click()
    If Me.CheckBox1.Caption = "Circle" And Me.CheckBox1 Then
        Me.TextBox2.Enabled = False
    Else
        Me.TextBox2.Enabled = True
    End If
    
End Sub

Private Sub TextBox1_Change()
    If Me.CheckBox1.Caption = "Circle" Then
        If Me.CheckBox1 Then Me.TextBox2 = Me.TextBox1
    End If
End Sub
