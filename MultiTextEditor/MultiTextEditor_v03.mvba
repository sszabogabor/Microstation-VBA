Attribute VB_Name = "Module1"
Sub start_mte()
   
    UserForm1.Show
    'On Error GoTo finish
    '
'finish:
    'MsgBox "Fatal error!"
    'End
End Sub


''''''''''''''
'Szabo Gabor '08

Sub whataelement()



    Dim oEnumerator As ElementEnumerator
        Dim oSelected As Element
        
        
        Set oEnumerator = ActiveModelReference.GetSelectedElements
        
        Do While (oEnumerator.MoveNext)
           
            Set oSelected = oEnumerator.Current
            Dim oType As MsdElementType
            oType = oSelected.Type
            
                Loop

End Sub

Attribute VB_Name = "UserForm1"
Attribute VB_Base = "0{9B857466-D35E-4B88-8B6F-A4AA663B6E45}{6A468DAF-15B6-4BD9-BE0F-4EDE3E7F5400}"
Attribute VB_GlobalNameSpace = False
Attribute VB_Creatable = False
Attribute VB_PredeclaredId = True
Attribute VB_Exposed = False
Attribute VB_TemplateDerived = False
Attribute VB_Customizable = False

Private Sub CommandButton1_Click()
    'prefix appendix
        Dim cislo As Double
        Dim oEnumerator As ElementEnumerator
        Set oEnumerator = ActiveModelReference.GetSelectedElements
        Dim oSelected_whata As Element
        Dim myText As String
        
        Do While (oEnumerator.MoveNext)
            Set oSelected_whata = oEnumerator.Current
            Dim whataelement As MsdElementType
            whataelement = oSelected_whata.Type
            'On Error GoTo errorhandler
            
            If whataelement = msdElementTypeText Then
                Dim oSelected As TextElement
                Set oSelected = oEnumerator.Current
                ID = oSelected.ID.Low
                myText = (oSelected.Text)
                oSelected.Text = Me.TextBox1.Text & myText & Me.TextBox2.Text
                oSelected.Rewrite
                oSelected.Redraw
                
            ElseIf whataelement = msdElementTypeTextNode Then
                Dim oSelectedTLE As TextNodeElement
                Set oSelectedTLE = oEnumerator.Current
                ID = oSelectedTLE.ID.Low
                If Me.CheckBox2 Then
                    chkb2 = oSelectedTLE.TextLinesCount
                Else
                    chkb2 = 1
                End If
                For i = 1 To chkb2
                    myText = oSelectedTLE.TextLine(i)
                    oSelectedTLE.TextLine(i) = Me.TextBox1.Text & myText & Me.TextBox2.Text
                    oSelectedTLE.Rewrite
                    oSelectedTLE.Redraw
                Next i
                
            ElseIf whataelement = msdElementTypeCellHeader Then
                Dim oCellHeader As CellElement
                Set oCellHeader = oSelected_whata
                                                
                Dim eleTemp As Element
                
                oCellHeader.ResetElementEnumeration
                Do While oCellHeader.MoveToNextElement(True)
                    Set eleTemp = oCellHeader.CopyCurrentElement
                    If eleTemp.IsTextNodeElement Then
                        Dim TNE As TextNodeElement
                        Set TNE = eleTemp
                        Set ee = TNE.GetSubElements
                        counter = 0
                        Do While (ee.MoveNext)
                          
                                Set elecomponent = ee.Current
                                If elecomponent.IsTextElement Then
                                    Dim fuckngtext As TextElement
                                    Set fuckngtext = elecomponent
                                    myText = fuckngtext.Text
                                    fuckngtext.Text = Me.TextBox1.Text & myText & Me.TextBox2.Text
                                    fuckngtext.Rewrite
                                    fuckngtext.Redraw
                                    counter = counter + 1
                                End If
                        If Me.CheckBox2 = False And counter > 0 Then
                            GoTo endLoop
                            'jinak to je svinstvo kamo
                        End If
                            
                        Loop
endLoop:
                    ElseIf eleTemp.IsTextElement Then
                        Dim textelem As TextElement
                        Set textelem = eleTemp
                        myText = textelem.Text
                        textelem.Text = Me.TextBox1.Text & myText & Me.TextBox2.Text
                        textelem.Rewrite
                        textelem.Redraw
                    End If
                    
                Loop
                  
            
            Else
            
            End If
        
errorhandler:
            'nenechame se vycukat
        Loop

End Sub

Private Sub CommandButton2_Click()
'replace
Dim cislo As Double
        Dim oEnumerator As ElementEnumerator
        Set oEnumerator = ActiveModelReference.GetSelectedElements
        Dim oSelected_whata As Element
        Dim myText As String
        Dim position As Integer
        Dim no_letter(192) As Integer '0 To 47, 58 To 64, 91 To 96, 123 To 255
        Dim nazacatku As Boolean
        Dim s_nazacatku  As Boolean
        Dim s_nakonci As Boolean
        
        'fill array no letter asci code
        For i = 0 To 46 '0 To 47
            no_letter(i) = i + 1
        Next i
        For i = 47 To 53 '58 To 64
            no_letter(i) = i + 11
        Next i
        For i = 54 To 60 '91 To 96
            no_letter(i) = i + 37
        Next i
        For i = 60 To 192 '123 To 255
            no_letter(i) = i + 63
        Next i
        
        Do While (oEnumerator.MoveNext)
            Set oSelected_whata = oEnumerator.Current
            Dim whataelement As MsdElementType
            whataelement = oSelected_whata.Type
            On Error GoTo errorhandler
            
            If whataelement = msdElementTypeText Then
                Dim oSelected As TextElement
                Set oSelected = oEnumerator.Current
                ID = oSelected.ID.Low
                myText = oSelected.Text
                mysearch = Me.TextBox3
                
                
                'Dim zicher As Integer
                
                'Do
                    'zicher = zicher + 1
                    'If zicher > 100000 Then Exit Do

                    myText = oSelected.Text
                    If Me.CheckBox1 Then
                        casesensitive = 0
                        position = InStr(1, myText, mysearch, casesensitive)
                    Else
                        casesensitive = 1
                        position = InStr(1, LCase(myText), LCase(mysearch), casesensitive)
                    End If
                    
                    If position <> 0 Then
                    
                        If Me.CheckBox3 Then
                            'jedine slovo slovo
                            If position = 1 And LCase(myText) = LCase(mysearch) Then
                                oSelected.Text = Replace(myText, mysearch, Me.TextBox4, , , casesensitive)
                                oSelected.Rewrite
                                oSelected.Redraw
                            
                            'prvni slovo je reseni pak znak
                            ElseIf position = 1 Then
                                For i = 1 To UBound(no_letter())
                                    'a = Mid(myText, Len(mysearch) + 1, 1)
                                    If Asc(Mid(myText, Len(mysearch) + 1, 1)) = no_letter(i) Then
                                        oSelected.Text = Replace(myText, mysearch, Me.TextBox4, , 1, casesensitive)
                                        oSelected.Rewrite
                                        oSelected.Redraw
                                        Exit For
                                    End If
                                Next i
                            'posleni sloveo je reseni prednim znak
                            ElseIf position = Len(myText) - Len(mysearch) + 1 Then
                                For i = 1 To UBound(no_letter())
                                    'a = Mid(myText, Len(myText) - Len(mysearch), 1)
                                    If Asc(Mid(myText, Len(myText) - Len(mysearch), 1)) = no_letter(i) Then
                                        oSelected.Text = Replace(myText, mysearch, Me.TextBox4, , 1, casesensitive)
                                        oSelected.Rewrite
                                        oSelected.Redraw
                                        Exit For
                                    End If
                                Next i
                            
                            Else
                            'stredni sloveo je reseni prednim a za nim znak
                                zacatek_ok = False
                                konec_ok = False
                                For i = 1 To UBound(no_letter())
                                    If Asc(Mid(myText, position - 1, 1)) = no_letter(i) Then
                                        zacatek_ok = True
                                    End If
                                    If Asc(Mid(myText, position + Len(mysearch), 1)) = no_letter(i) Then
                                        konec_ok = True
                                    End If
                                    If zacatek_ok And konec_ok Then
                                        oSelected.Text = Replace(myText, mysearch, Me.TextBox4, , 1, casesensitive)
                                        oSelected.Rewrite
                                        oSelected.Redraw
                                        Exit For
                                    End If
                                Next i
                            
                            End If
                      

                        Else
                            'NO WHOLE WORD
                            'delka = Len(mysearch)
                            'prvnicast = Mid(myText, 1, position - 1)
                            'treticast = Mid(myText, position + delka, Len(myText))
                            
                            'oSelected.Text = prvnicast & Me.TextBox4.Text & treticast
                            oSelected.Text = Replace(myText, mysearch, Me.TextBox4, , , casesensitive)
                            oSelected.Rewrite
                            oSelected.Redraw
                    End If
                    
                End If
                    
                    
                'Loop
                
            ElseIf whataelement = msdElementTypeTextNode Then
                Dim oSelectedTLE As TextNodeElement
                Set oSelectedTLE = oEnumerator.Current
                ID = oSelectedTLE.ID.Low
                mysearch = Me.TextBox3
                
                If Me.CheckBox2 Then
                    TLOpt_lines = oSelectedTLE.TextLinesCount
                Else
                    TLOpt_lines = 1
                End If
                
                For k = 1 To TLOpt_lines
                    myText = oSelectedTLE.TextLine(k)
                    
                    'Dim zicherTLE As Integer
                    
                    'Do
                        'zicherTLE = zicherTLE + 1
                        'If zicherTLE > 100000 Then Exit Do
    
                        myText = oSelectedTLE.TextLine(k)
                        
                        If Me.CheckBox1 Then
                            casesensitive = 0
                            position = InStr(1, myText, mysearch, casesensitive)
                        Else
                            casesensitive = 1
                            position = InStr(1, LCase(myText), LCase(mysearch), casesensitive)
                        End If
                        
                        If position <> 0 Then
                        
                            If Me.CheckBox3 Then
                                'jedine slovo slovo
                                If position = 1 And LCase(myText) = LCase(mysearch) Then
                                    oSelectedTLE.TextLine(k) = Replace(myText, mysearch, Me.TextBox4, , , casesensitive)
                                    oSelectedTLE.Rewrite
                                    oSelectedTLE.Redraw
                                
                                'prvni slovo je reseni pak znak
                                ElseIf position = 1 Then
                                    For i = 1 To UBound(no_letter())
                                        'a = Mid(myText, Len(mysearch) + 1, 1)
                                        If Asc(Mid(myText, Len(mysearch) + 1, 1)) = no_letter(i) Then
                                            oSelectedTLE.TextLine(k) = Replace(myText, mysearch, Me.TextBox4, , 1, casesensitive)
                                            oSelectedTLE.Rewrite
                                            oSelectedTLE.Redraw
                                            Exit For
                                        End If
                                    Next i
                                'posleni sloveo je reseni prednim znak
                                ElseIf position = Len(myText) - Len(mysearch) + 1 Then
                                    For i = 1 To UBound(no_letter())
                                        'a = Mid(myText, Len(myText) - Len(mysearch), 1)
                                        If Asc(Mid(myText, Len(myText) - Len(mysearch), 1)) = no_letter(i) Then
                                            oSelectedTLE.TextLine(k) = Replace(myText, mysearch, Me.TextBox4, , 1, casesensitive)
                                            oSelectedTLE.Rewrite
                                            oSelectedTLE.Redraw
                                            Exit For
                                        End If
                                    Next i
                                
                                Else
                                'stredni sloveo je reseni prednim a za nim znak
                                    zacatek_ok = False
                                    konec_ok = False
                                    For i = 1 To UBound(no_letter())
                                        If Asc(Mid(myText, position - 1, 1)) = no_letter(i) Then
                                            zacatek_ok = True
                                        End If
                                        If Asc(Mid(myText, position + Len(mysearch), 1)) = no_letter(i) Then
                                            konec_ok = True
                                        End If
                                        If zacatek_ok And konec_ok Then
                                            oSelectedTLE.TextLine(k) = Replace(myText, mysearch, Me.TextBox4, , 1, casesensitive)
                                            oSelectedTLE.Rewrite
                                            oSelectedTLE.Redraw
                                            Exit For
                                        End If
                                    Next i
                                
                                End If
                            
    
                            Else
                                'NO WHOLE WORD
                                oSelectedTLE.TextLine(k) = Replace(myText, mysearch, Me.TextBox4, , , casesensitive)
                                oSelectedTLE.Rewrite
                                oSelectedTLE.Redraw
                            End If
                        End If

                    'Loop
                Next k
                
            ElseIf whataelement = msdElementTypeCellHeader Then
                Dim oCellHeader As CellElement
                Set oCellHeader = oSelected_whata
                                                
                Dim eleTemp As Element
                
                mysearch = Me.TextBox3
                
                oCellHeader.ResetElementEnumeration
                Do While oCellHeader.MoveToNextElement(True)
                    Set eleTemp = oCellHeader.CopyCurrentElement
                    If eleTemp.IsTextNodeElement Then
                        Dim TNE As TextNodeElement
                        Set TNE = eleTemp
                        Set ee = TNE.GetSubElements
                        counter = 0
                        Do While (ee.MoveNext)
                                Set elecomponent = ee.Current
                                If elecomponent.IsTextElement Then
                                    Dim fuckngtext As TextElement
                                    Set fuckngtext = elecomponent
                                    myText = fuckngtext.Text
                                    
                                    If Me.CheckBox1 Then
                                        casesensitive = 0
                                    Else
                                        casesensitive = 1
                                    End If
                                    
                                    fuckngtext.Text = Replace(myText, mysearch, Me.TextBox4, , , casesensitive)
                                    fuckngtext.Rewrite
                                    fuckngtext.Redraw
                                    counter = counter + 1
                                End If
                        If Me.CheckBox2 And counter > 0 Then
                            GoTo endLoop
                            'jinak to je svinstvo kamo
                        End If
                            
                        Loop
endLoop:
                        ElseIf eleTemp.IsTextElement Then
                        Dim textelem As TextElement
                        Set textelem = eleTemp
                        myText = textelem.Text
                        textelem.Text = Replace(myText, mysearch, Me.TextBox4, , , casesensitive)
                        textelem.Rewrite
                        textelem.Redraw
                    End If
                    
                Loop
                
            Else
            
            End If
        
errorhandler:
            'nenechame se vycukat
        Loop
End Sub

Private Sub CommandButton3_Click()
        'all AAAA
        Dim oEnumerator As ElementEnumerator
        Set oEnumerator = ActiveModelReference.GetSelectedElements
        Dim oSelected_whata As Element
        Dim myText As String
        
        Do While (oEnumerator.MoveNext)
            Set oSelected_whata = oEnumerator.Current
            Dim whataelement As MsdElementType
            whataelement = oSelected_whata.Type
            On Error GoTo errorhandler
            
            If whataelement = msdElementTypeText Then
                Dim oSelected As TextElement
                Set oSelected = oEnumerator.Current
                ID = oSelected.ID.Low
                myText = (oSelected.Text)
                oSelected.Text = UCase(myText)
                oSelected.Rewrite
                oSelected.Redraw
                
            ElseIf whataelement = msdElementTypeTextNode Then
                Dim oSelectedTLE As TextNodeElement
                Set oSelectedTLE = oEnumerator.Current
                ID = oSelectedTLE.ID.Low
                If Me.CheckBox2 Then
                    chkb2 = oSelectedTLE.TextLinesCount
                Else
                    chkb2 = 1
                End If
                For i = 1 To chkb2
                    myText = oSelectedTLE.TextLine(i)
                    oSelectedTLE.TextLine(i) = UCase(myText)
                    oSelectedTLE.Rewrite
                    oSelectedTLE.Redraw
                Next i
            ElseIf whataelement = msdElementTypeCellHeader Then
                Dim oCellHeader As CellElement
                Set oCellHeader = oSelected_whata
                                                
                Dim eleTemp As Element
                
                mysearch = Me.TextBox3
                
                oCellHeader.ResetElementEnumeration
                Do While oCellHeader.MoveToNextElement(True)
                    Set eleTemp = oCellHeader.CopyCurrentElement
                    If eleTemp.IsTextNodeElement Then
                        Dim TNE As TextNodeElement
                        Set TNE = eleTemp
                        Set ee = TNE.GetSubElements
                        counter = 0
                        Do While (ee.MoveNext)
                                Set elecomponent = ee.Current
                                If elecomponent.IsTextElement Then
                                    Dim fuckngtext As TextElement
                                    Set fuckngtext = elecomponent
                                    myText = fuckngtext.Text
                                    
                                    fuckngtext.Text = UCase(myText)
                                    fuckngtext.Rewrite
                                    fuckngtext.Redraw
                                    counter = counter + 1
                                End If
                        If Me.CheckBox2 = False And counter > 0 Then
                            GoTo endLoop
                            'jinak to je svinstvo kamo
                        End If
                            
                        Loop
endLoop:
                    ElseIf eleTemp.IsTextElement Then
                        Dim textelem As TextElement
                        Set textelem = eleTemp
                        myText = textelem.Text
                        textelem.Text = UCase(myText)
                        textelem.Rewrite
                        textelem.Redraw
                    End If
                    
                Loop
                
            Else
    
            
            End If
        
errorhandler:
            'nenechame se vycukat
        Loop
End Sub

Private Sub CommandButton4_Click()
        'all aaa
        Dim oEnumerator As ElementEnumerator
        Set oEnumerator = ActiveModelReference.GetSelectedElements
        Dim oSelected_whata As Element
        Dim myText As String
        
        Do While (oEnumerator.MoveNext)
            Set oSelected_whata = oEnumerator.Current
            Dim whataelement As MsdElementType
            whataelement = oSelected_whata.Type
            On Error GoTo errorhandler
            
            If whataelement = msdElementTypeText Then
                Dim oSelected As TextElement
                Set oSelected = oEnumerator.Current
                ID = oSelected.ID.Low
                myText = (oSelected.Text)
                oSelected.Text = LCase(myText)
                oSelected.Rewrite
                oSelected.Redraw
                
            ElseIf whataelement = msdElementTypeTextNode Then
                Dim oSelectedTLE As TextNodeElement
                Set oSelectedTLE = oEnumerator.Current
                ID = oSelectedTLE.ID.Low
                If Me.CheckBox2 Then
                    chkb2 = oSelectedTLE.TextLinesCount
                Else
                    chkb2 = 1
                End If
                For i = 1 To chkb2
                    myText = oSelectedTLE.TextLine(i)
                    oSelectedTLE.TextLine(i) = LCase(myText)
                    oSelectedTLE.Rewrite
                    oSelectedTLE.Redraw
                Next i
                
            ElseIf whataelement = msdElementTypeCellHeader Then
                Dim oCellHeader As CellElement
                Set oCellHeader = oSelected_whata
                                                
                Dim eleTemp As Element
                
                mysearch = Me.TextBox3
                
                oCellHeader.ResetElementEnumeration
                Do While oCellHeader.MoveToNextElement(True)
                    Set eleTemp = oCellHeader.CopyCurrentElement
                    If eleTemp.IsTextNodeElement Then
                        Dim TNE As TextNodeElement
                        Set TNE = eleTemp
                        Set ee = TNE.GetSubElements
                        counter = 0
                        Do While (ee.MoveNext)
                                Set elecomponent = ee.Current
                                If elecomponent.IsTextElement Then
                                    Dim fuckngtext As TextElement
                                    Set fuckngtext = elecomponent
                                    myText = fuckngtext.Text
                                    
                                    fuckngtext.Text = LCase(myText)
                                    fuckngtext.Rewrite
                                    fuckngtext.Redraw
                                    counter = counter + 1
                                End If
                        If Me.CheckBox2 = False And counter > 0 Then
                            GoTo endLoop
                            'jinak to je svinstvo kamo
                        End If
                            
                        Loop
endLoop:
                    ElseIf eleTemp.IsTextElement Then
                        Dim textelem As TextElement
                        Set textelem = eleTemp
                        myText = textelem.Text
                        textelem.Text = LCase(myText)
                        textelem.Rewrite
                        textelem.Redraw
                    End If
                    
                Loop
                
            Else
            
            End If
        
errorhandler:
            'nenechame se vycukat
        Loop
End Sub

Private Sub CommandButton5_Click()
   'all Aaaa
    Dim oEnumerator As ElementEnumerator
        Set oEnumerator = ActiveModelReference.GetSelectedElements
        Dim oSelected_whata As Element
        Dim myText As String
        
        Do While (oEnumerator.MoveNext)
            Set oSelected_whata = oEnumerator.Current
            Dim whataelement As MsdElementType
            whataelement = oSelected_whata.Type
            On Error GoTo errorhandler
            
            If whataelement = msdElementTypeText Then
                Dim oSelected As TextElement
                Set oSelected = oEnumerator.Current
                ID = oSelected.ID.Low
                myText = (oSelected.Text)
                oSelected.Text = UCase(Mid(myText, 1, 1)) & LCase(Mid(myText, 2, Len(myText)))
                oSelected.Rewrite
                oSelected.Redraw
                
            ElseIf whataelement = msdElementTypeTextNode Then
                Dim oSelectedTLE As TextNodeElement
                Set oSelectedTLE = oEnumerator.Current
                ID = oSelectedTLE.ID.Low
                If Me.CheckBox2 Then
                    chkb2 = oSelectedTLE.TextLinesCount
                Else
                    chkb2 = 1
                End If
                For i = 1 To chkb2
                    myText = oSelectedTLE.TextLine(i)
                    oSelectedTLE.TextLine(i) = UCase(Mid(myText, 1, 1)) & LCase(Mid(myText, 2, Len(myText)))
                    oSelectedTLE.Rewrite
                    oSelectedTLE.Redraw
                Next i
                
            ElseIf whataelement = msdElementTypeCellHeader Then
                Dim oCellHeader As CellElement
                Set oCellHeader = oSelected_whata
                                                
                Dim eleTemp As Element
                
                mysearch = Me.TextBox3
                
                oCellHeader.ResetElementEnumeration
                Do While oCellHeader.MoveToNextElement(True)
                    Set eleTemp = oCellHeader.CopyCurrentElement
                    If eleTemp.IsTextNodeElement Then
                        Dim TNE As TextNodeElement
                        Set TNE = eleTemp
                        Set ee = TNE.GetSubElements
                        counter = 0
                        Do While (ee.MoveNext)
                                Set elecomponent = ee.Current
                                If elecomponent.IsTextElement Then
                                    Dim fuckngtext As TextElement
                                    Set fuckngtext = elecomponent
                                    myText = fuckngtext.Text
                                    
                                    fuckngtext.Text = UCase(Mid(myText, 1, 1)) & LCase(Mid(myText, 2, Len(myText)))
                                    fuckngtext.Rewrite
                                    fuckngtext.Redraw
                                    counter = counter + 1
                                End If
                        If Me.CheckBox2 = False And counter > 0 Then
                            GoTo endLoop
                            'jinak to je svinstvo kamo
                        End If
                            
                        Loop
endLoop:
                    ElseIf eleTemp.IsTextElement Then
                        Dim textelem As TextElement
                        Set textelem = eleTemp
                        myText = textelem.Text
                        textelem.Text = UCase(Mid(myText, 1, 1)) & LCase(Mid(myText, 2, Len(myText)))
                        textelem.Rewrite
                        textelem.Redraw
                    End If
                    
                Loop
                
            Else
            
            End If
        
errorhandler:
            'nenechame se vycukat
        Loop
End Sub

Private Sub CommandButton6_Click()
        'divide text node to text line
        Dim oEnumerator As ElementEnumerator
        Set oEnumerator = ActiveModelReference.GetSelectedElements
        
        Do While (oEnumerator.MoveNext)
            Set oSelected_whata = oEnumerator.Current
            Dim whataelement As MsdElementType
            whataelement = oSelected_whata.Type
            On Error GoTo errorhandler
                
            If whataelement = msdElementTypeTextNode Then
                '
                Dim oSelectedTLE As TextNodeElement
                Set oSelectedTLE = oEnumerator.Current
                ID = oSelectedTLE.ID.Low
                Dim text_point As Point3d
                Dim text_rot As Matrix3d
                text_point = oSelectedTLE.Origin
                text_rot = oSelectedTLE.Rotation
                text_heigth = ActiveSettings.TextStyle.Height
                
                Dim oTe As TextElement
                
                For i = 1 To oSelectedTLE.TextLinesCount
                    text_point.Y = text_point.Y - CDbl(Replace(Me.TextBox5.Value, ".", ","))
                    If oSelectedTLE.TextLine(i) <> "" Then
                        Set oTe = CreateTextElement1(Nothing, oSelectedTLE.TextLine(i), text_point, text_rot)
                        ActiveModelReference.AddElement oTe
                        oTe.Redraw
                    End If
                Next i
                
                If Me.CheckBox4 Then oSelectedTLE.DeleteAllTextLines
                    
            End If
            
errorhandler:

        Loop
            
End Sub

Private Sub CommandButton7_Click()
    'overwrite
    Dim oEnumerator As ElementEnumerator
        Set oEnumerator = ActiveModelReference.GetSelectedElements
        Dim oSelected_whata As Element
        Dim myText As String
        
        Do While (oEnumerator.MoveNext)
            Set oSelected_whata = oEnumerator.Current
            Dim whataelement As MsdElementType
            whataelement = oSelected_whata.Type
            On Error GoTo errorhandler
            
            If whataelement = msdElementTypeText Then
                Dim oSelected As TextElement
                Set oSelected = oEnumerator.Current
                ID = oSelected.ID.Low
                
                oSelected.Text = Me.TextBox6
                oSelected.Rewrite
                oSelected.Redraw
                
            ElseIf whataelement = msdElementTypeTextNode Then
                Dim oSelectedTLE As TextNodeElement
                Set oSelectedTLE = oEnumerator.Current
                ID = oSelectedTLE.ID.Low
                If Me.CheckBox2 Then
                    chkb2 = oSelectedTLE.TextLinesCount
                Else
                    chkb2 = 1
                End If
                For i = 1 To chkb2
                    myText = oSelectedTLE.TextLine(i)
                    oSelectedTLE.TextLine(i) = Me.TextBox6
                    oSelectedTLE.Rewrite
                    oSelectedTLE.Redraw
                Next i
                
            ElseIf whataelement = msdElementTypeCellHeader Then
                Dim oCellHeader As CellElement
                Set oCellHeader = oSelected_whata
                                                
                Dim eleTemp As Element
                
                mysearch = Me.TextBox3
                
                oCellHeader.ResetElementEnumeration
                Do While oCellHeader.MoveToNextElement(True)
                    Set eleTemp = oCellHeader.CopyCurrentElement
                    If eleTemp.IsTextNodeElement Then
                        Dim TNE As TextNodeElement
                        Set TNE = eleTemp
                        Set ee = TNE.GetSubElements
                        counter = 0
                        Do While (ee.MoveNext)
                                Set elecomponent = ee.Current
                                If elecomponent.IsTextElement Then
                                    Dim fuckngtext As TextElement
                                    Set fuckngtext = elecomponent
                                    myText = fuckngtext.Text
                                    
                                    fuckngtext.Text = Me.TextBox6
                                    fuckngtext.Rewrite
                                    fuckngtext.Redraw
                                    counter = counter + 1
                                End If
                        If Me.CheckBox2 = False And counter > 0 Then
                            GoTo endLoop
                            'jinak to je svinstvo kamo
                        End If
                            
                        Loop
endLoop:
                    ElseIf eleTemp.IsTextElement Then
                        Dim textelem As TextElement
                        Set textelem = eleTemp
                        myText = textelem.Text
                        textelem.Text = Me.TextBox6
                        textelem.Rewrite
                        textelem.Redraw
                    End If
                    
                Loop
                
            Else
            
            End If
        
errorhandler:
            'nenechame se vycukat
        Loop
End Sub

Private Sub Label3_Click()
    Dim oEnumerator As ElementEnumerator
    Set oEnumerator = ActiveModelReference.GetSelectedElements
    
    Do While (oEnumerator.MoveNext)
            Set oSelected_whata = oEnumerator.Current
            Dim whataelement As MsdElementType
            whataelement = oSelected_whata.Type
            On Error GoTo errorhandler
                
            If whataelement = msdElementTypeTextNode Then
                '
                Dim oSelectedTLE As TextNodeElement
                Set oSelectedTLE = oEnumerator.Current
                ID = oSelectedTLE.ID.Low
                Me.TextBox5 = oSelectedTLE.LineSpacing + ActiveSettings.TextStyle.Height
                Exit Sub
            
            End If
            
errorhandler:

        Loop
End Sub

Private Sub CommandButton8_Click()
    'UNDERLINE
    Dim oEnumerator As ElementEnumerator
        Set oEnumerator = ActiveModelReference.GetSelectedElements
        Dim oSelected_whata As Element
        Dim myText As String
        
        Do While (oEnumerator.MoveNext)
            Set oSelected_whata = oEnumerator.Current
            Dim whataelement As MsdElementType
            whataelement = oSelected_whata.Type
            'On Error GoTo errorhandler
            
           
            
            If whataelement = msdElementTypeText Then
                Dim oSelected As TextElement
                Set oSelected = oEnumerator.Current
                ID = oSelected.ID.Low
                
                If oSelected.TextStyle.IsUnderlined = True Then
                    oSelected.TextStyle.IsUnderlined = False
                ElseIf oSelected.TextStyle.IsUnderlined = False Then
                    oSelected.TextStyle.IsUnderlined = True
                End If

                oSelected.Rewrite
                oSelected.Redraw
                
            ElseIf whataelement = msdElementTypeTextNode Then
                Dim oSelectedTLE As TextNodeElement
                Set oSelectedTLE = oEnumerator.Current
                Set ee = oSelectedTLE.GetSubElements
                        counter = 0
                        Do While (ee.MoveNext)
                            Set elecomponent = ee.Current
                                If elecomponent.IsTextElement Then
                                    Dim textel As TextElement
                                    Set textel = elecomponent
                                    If textel.TextStyle.IsUnderlined = True Then
                                        textel.TextStyle.IsUnderlined = False
                                    ElseIf textel.TextStyle.IsUnderlined = False Then
                                        textel.TextStyle.IsUnderlined = True
                                    End If
                                    counter = counter + 1
                                End If
                            
                            If Me.CheckBox2 And counter > 0 Then
                                GoTo endLoop
                                'jinak to je svinstvo kamo
                            End If
                            
                        Loop
endLoop:
                    
                
                
            ElseIf whataelement = msdElementTypeCellHeader Then
                Dim oCellHeader As CellElement
                Set oCellHeader = oSelected_whata
                                                
                Dim eleTemp As Element
                
                mysearch = Me.TextBox3
                
                oCellHeader.ResetElementEnumeration
                Do While oCellHeader.MoveToNextElement(True)
                    Set eleTemp = oCellHeader.CopyCurrentElement
                    If eleTemp.IsTextNodeElement Then
                        Dim TNE As TextNodeElement
                        Set TNE = eleTemp
                        Set ee = TNE.GetSubElements
                        counter = 0
                        Do While (ee.MoveNext)
                                Set elecomponent = ee.Current
                                If elecomponent.IsTextElement Then
                                    Dim textele As TextElement
                                    Set textele = elecomponent
                                    If textele.TextStyle.IsUnderlined = True Then
                                        textele.TextStyle.IsUnderlined = False
                                    ElseIf textele.TextStyle.IsUnderlined = False Then
                                        textele.TextStyle.IsUnderlined = True
                                    End If
                                    textele.Rewrite
                                    textele.Redraw
                                    counter = counter + 1
                                End If
                        If Me.CheckBox2 = False And counter > 0 Then
                            GoTo endLoop1
                            'jinak to je svinstvo kamo
                        End If
                            
                        Loop
endLoop1:
                    End If
                    
                Loop
                
            Else
            
            End If
        
errorhandler:
            'nenechame se vycukat
        Loop
End Sub
