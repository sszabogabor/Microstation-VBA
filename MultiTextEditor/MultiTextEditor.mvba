Attribute VB_Name = "Module1"
Sub start_mte()
   
    UserForm1.Show
    'On Error GoTo finish
    '
'finish:
    'MsgBox "Fatal error!"
    'End
End Sub


''''''''''''''
'Szabo Gabor '08

Sub whataelement()



    Dim oEnumerator As ElementEnumerator
        Dim oSelected As Element
        
        
        Set oEnumerator = ActiveModelReference.GetSelectedElements
        
        Do While (oEnumerator.MoveNext)
           
            Set oSelected = oEnumerator.Current
            Dim oType As MsdElementType
            oType = oSelected.Type
            
                Loop

End Sub

Attribute VB_Name = "UserForm1"
Attribute VB_Base = "0{DBFE8350-F4B0-4174-A00A-A85C5AD36033}{CA28A8A6-C82F-41C3-B07A-0A4B352163B5}"
Attribute VB_GlobalNameSpace = False
Attribute VB_Creatable = False
Attribute VB_PredeclaredId = True
Attribute VB_Exposed = False
Attribute VB_TemplateDerived = False
Attribute VB_Customizable = False
Private Sub CommandButton1_Click()
        
        Dim cislo As Double
        Dim oEnumerator As ElementEnumerator
        Set oEnumerator = ActiveModelReference.GetSelectedElements
        Dim oSelected_whata As Element
        Dim myText As String
        
        Do While (oEnumerator.MoveNext)
            Set oSelected_whata = oEnumerator.Current
            Dim whataelement As MsdElementType
            whataelement = oSelected_whata.Type
            On Error GoTo errorhandler
            
            If whataelement = msdElementTypeText Then
                Dim oSelected As TextElement
                Set oSelected = oEnumerator.Current
                ID = oSelected.ID.Low
                myText = (oSelected.Text)
                oSelected.Text = Me.TextBox1.Text & myText & Me.TextBox2.Text
                oSelected.Rewrite
                oSelected.Redraw
                
            ElseIf whataelement = msdElementTypeTextNode Then
                Dim oSelectedTLE As TextNodeElement
                Set oSelectedTLE = oEnumerator.Current
                ID = oSelectedTLE.ID.Low
                myText = CDbl(oSelectedTLE.TextLine(1))
                oSelected.Text = Me.TextBox1.Text & myText & Me.TextBox2.Text
                oSelected.Rewrite
                oSelected.Redraw
                
            Else
            
            End If
        
errorhandler:
            'nenechame se vycukat
        Loop

End Sub

Private Sub CommandButton2_Click()
Dim cislo As Double
        Dim oEnumerator As ElementEnumerator
        Set oEnumerator = ActiveModelReference.GetSelectedElements
        Dim oSelected_whata As Element
        Dim myText As String
        Dim position As Integer
        
        Do While (oEnumerator.MoveNext)
            Set oSelected_whata = oEnumerator.Current
            Dim whataelement As MsdElementType
            whataelement = oSelected_whata.Type
            On Error GoTo errorhandler
            
            If whataelement = msdElementTypeText Then
                Dim oSelected As TextElement
                Set oSelected = oEnumerator.Current
                ID = oSelected.ID.Low
                myText = oSelected.Text
                mysearch = Me.TextBox3
                If Me.CheckBox1 Then
                    casesensitive = 0
                Else
                    casesensitive = 1
                End If
                position = InStr(1, myText, mysearch, casesensitive)
                delka = Len(mysearch)
                prvnicast = Mid(myText, 1, position - 1)
                treticast = Mid(myText, position + delka, Len(myText))
                
                oSelected.Text = prvnicast & Me.TextBox4.Text & treticast
                oSelected.Rewrite
                oSelected.Redraw
                
            ElseIf whataelement = msdElementTypeTextNode Then
                Dim oSelectedTLE As TextNodeElement
                Set oSelectedTLE = oEnumerator.Current
                ID = oSelectedTLE.ID.Low
                myText = oSelectedTLE.TextLine(1)
                mysearch = Me.TextBox3
                If Me.CheckBox1 Then
                    casesensitive = 0
                Else
                    casesensitive = 1
                End If
                position = InStr(1, myText, mysearch, casesensitive)
                delka = Len(mysearch)
                prvnicast = Mid(myText, 1, position - 1)
                treticast = Mid(myText, position + delka, Len(myText))
                              
                oSelectedTLE.TextLine(1) = prvnicast & Me.TextBox4.Text & treticast
                oSelectedTLE.Rewrite
                oSelectedTLE.Redraw
                
            Else
            
            End If
        
errorhandler:
            'nenechame se vycukat
        Loop
End Sub
