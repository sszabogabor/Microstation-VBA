Attribute VB_Name = "Module1"
Sub start_mte()
   
    UserForm1.Show
    'On Error GoTo finish
    '
'finish:
    'MsgBox "Fatal error!"
    'End
End Sub


''''''''''''''
'Szabo Gabor '08

Sub whataelement()



    Dim oEnumerator As ElementEnumerator
        Dim oSelected As Element
        
        
        Set oEnumerator = ActiveModelReference.GetSelectedElements
        
        Do While (oEnumerator.MoveNext)
           
            Set oSelected = oEnumerator.Current
            Dim oType As MsdElementType
            oType = oSelected.Type
            
                Loop

End Sub

Attribute VB_Name = "UserForm1"
Attribute VB_Base = "0{228EE217-8711-44C9-9A5C-A046038CB15F}{81949A23-FB99-49BD-A0C6-B945AE5A94C1}"
Attribute VB_GlobalNameSpace = False
Attribute VB_Creatable = False
Attribute VB_PredeclaredId = True
Attribute VB_Exposed = False
Attribute VB_TemplateDerived = False
Attribute VB_Customizable = False

Private Sub CommandButton1_Click()
    'prefix appendix
        Dim cislo As Double
        Dim oEnumerator As ElementEnumerator
        Set oEnumerator = ActiveModelReference.GetSelectedElements
        Dim oSelected_whata As Element
        Dim myText As String
        
        Do While (oEnumerator.MoveNext)
            Set oSelected_whata = oEnumerator.Current
            Dim whataelement As MsdElementType
            whataelement = oSelected_whata.Type
            On Error GoTo errorhandler
            
            If whataelement = msdElementTypeText Then
                Dim oSelected As TextElement
                Set oSelected = oEnumerator.Current
                ID = oSelected.ID.Low
                myText = (oSelected.Text)
                oSelected.Text = Me.TextBox1.Text & myText & Me.TextBox2.Text
                oSelected.Rewrite
                oSelected.Redraw
                
            ElseIf whataelement = msdElementTypeTextNode Then
                Dim oSelectedTLE As TextNodeElement
                Set oSelectedTLE = oEnumerator.Current
                ID = oSelectedTLE.ID.Low
                If Me.CheckBox2 Then
                    chkb2 = oSelectedTLE.TextLinesCount
                Else
                    chkb2 = 1
                End If
                For i = 1 To chkb2
                    myText = oSelectedTLE.TextLine(i)
                    oSelectedTLE.TextLine(i) = Me.TextBox1.Text & myText & Me.TextBox2.Text
                    oSelectedTLE.Rewrite
                    oSelectedTLE.Redraw
                Next i
                
            Else
            
            End If
        
errorhandler:
            'nenechame se vycukat
        Loop

End Sub

Private Sub CommandButton2_Click()
'replace
Dim cislo As Double
        Dim oEnumerator As ElementEnumerator
        Set oEnumerator = ActiveModelReference.GetSelectedElements
        Dim oSelected_whata As Element
        Dim myText As String
        Dim position As Integer
        Dim no_letter(192) As Integer '0 To 47, 58 To 64, 91 To 96, 123 To 255
        Dim nazacatku As Boolean
        Dim s_nazacatku  As Boolean
        Dim s_nakonci As Boolean
        
        'fill array no letter asci code
        For i = 0 To 46 '0 To 47
            no_letter(i) = i + 1
        Next i
        For i = 47 To 53 '58 To 64
            no_letter(i) = i + 11
        Next i
        For i = 54 To 60 '91 To 96
            no_letter(i) = i + 37
        Next i
        For i = 60 To 192 '123 To 255
            no_letter(i) = i + 63
        Next i
        
        Do While (oEnumerator.MoveNext)
            Set oSelected_whata = oEnumerator.Current
            Dim whataelement As MsdElementType
            whataelement = oSelected_whata.Type
            On Error GoTo errorhandler
            
            If whataelement = msdElementTypeText Then
                Dim oSelected As TextElement
                Set oSelected = oEnumerator.Current
                ID = oSelected.ID.Low
                myText = oSelected.Text
                mysearch = Me.TextBox3
                If Me.CheckBox1 Then
                    casesensitive = 0
                Else
                    casesensitive = 1
                End If
                
                position = InStr(1, myText, mysearch, casesensitive)
                
                If Me.CheckBox3 Then
                    'zacatek zjistime jestli na konci a zacatku slova jsou pisma nebo ne
                    For i = 1 To UBound(no_letter())
                        If Asc(Mid(myText, Len(mysearch) + 1, 1)) = no_letter(i) Then
                            nazacatku = True
                        End If
                        'stredni slovo
                        If Not position = 1 Then
                            If Asc(Mid(myText, position - 1, 1)) = no_letter(i) Then
                                s_nazacatku = True
                            End If
                        End If
                        If Not position + Len(mysearch) - 1 = Len(myText) Then
                            If Asc(Mid(myText, position + Len(mysearch), 1)) = no_letter(i) Then
                                s_nakonci = True
                            End If
                       End If
                    Next i
                
                    If position = 1 And nazacatku Then
                        oSelected.Text = Replace(myText, mysearch, Me.TextBox4, , , casesensitive)
                        oSelected.Rewrite
                        oSelected.Redraw
                    ElseIf position = Len(myText) - Len(mysearch) + 1 Then
                        oSelected.Text = Replace(myText, mysearch, Me.TextBox4, , , casesensitive)
                        oSelected.Rewrite
                        oSelected.Redraw
                    ElseIf s_nakonci And s_nazacatku Then
                        oSelected.Text = Replace(myText, mysearch, Me.TextBox4, , , casesensitive)
                        oSelected.Rewrite
                        oSelected.Redraw
                    End If
                Else
                
                    'delka = Len(mysearch)
                    'prvnicast = Mid(myText, 1, position - 1)
                    'treticast = Mid(myText, position + delka, Len(myText))
                    
                    'oSelected.Text = prvnicast & Me.TextBox4.Text & treticast
                    oSelected.Text = Replace(myText, mysearch, Me.TextBox4)
                    oSelected.Rewrite
                    oSelected.Redraw
                
                End If
                nazacatku = False
            ElseIf whataelement = msdElementTypeTextNode Then
                Dim oSelectedTLE As TextNodeElement
                Set oSelectedTLE = oEnumerator.Current
                ID = oSelectedTLE.ID.Low
                
                mysearch = Me.TextBox3
                If Me.CheckBox1 Then
                    casesensitive = 0
                Else
                    casesensitive = 1
                End If
                'repalce
                For i = 1 To oSelectedTLE.TextLinesCount
                    myText = oSelectedTLE.TextLine(i)
                    position = InStr(1, myText, mysearch, casesensitive)
                    
                    
                    If Me.CheckBox3 Then
                        'zacatek zjistime jestli na konci a zacatku slova jsou pisma nebo ne
                        For j = 1 To UBound(no_letter())
                            If Asc(Mid(myText, Len(mysearch) + 1, 1)) = no_letter(j) Then
                                nazacatku = True
                            End If
                            'stredni slovo
                            If position <> 1 Or position <> 0 Then
                                If Asc(Mid(myText, position - 1, 1)) = no_letter(j) Then
                                    s_nazacatku = True
                                End If
                            End If
                            If Not position + Len(mysearch) - 1 = Len(myText) Then
                                If Asc(Mid(myText, position + Len(mysearch), 1)) = no_letter(j) Then
                                    s_nakonci = True
                                End If
                           End If
                        Next j
                    
                
                        If position = 1 And nazacatku = " " Then
                            oSelectedTLE.TextLine(i) = Replace(myText, mysearch, Me.TextBox4, , , casesensitive)
                            oSelectedTLE.Rewrite
                            oSelectedTLE.Redraw
                        ElseIf position = Len(myText) - Len(mysearch) + 1 Then
                            oSelectedTLE.TextLine(i) = Replace(myText, mysearch, Me.TextBox4, , , casesensitive)
                            oSelectedTLE.Rewrite
                            oSelectedTLE.Redraw
                       ElseIf s_nakonci And s_nazacatku Then
                            oSelectedTLE.TextLine(i) = Replace(myText, mysearch, Me.TextBox4, , , casesensitive)
                            oSelectedTLE.Rewrite
                            oSelectedTLE.Redraw
                        End If
                        
                    Else
                        
                        delka = Len(mysearch)
                        prvnicast = Mid(myText, 1, position - 1)
                        treticast = Mid(myText, position + delka, Len(myText))
                                      
                        oSelectedTLE.TextLine(i) = prvnicast & Me.TextBox4.Text & treticast
                        oSelectedTLE.Rewrite
                        oSelectedTLE.Redraw
                    End If
                Next i
                
            Else
            
            End If
        
errorhandler:
            'nenechame se vycukat
        Loop
End Sub

Private Sub CommandButton3_Click()
        'all AAAA
        Dim oEnumerator As ElementEnumerator
        Set oEnumerator = ActiveModelReference.GetSelectedElements
        Dim oSelected_whata As Element
        Dim myText As String
        
        Do While (oEnumerator.MoveNext)
            Set oSelected_whata = oEnumerator.Current
            Dim whataelement As MsdElementType
            whataelement = oSelected_whata.Type
            On Error GoTo errorhandler
            
            If whataelement = msdElementTypeText Then
                Dim oSelected As TextElement
                Set oSelected = oEnumerator.Current
                ID = oSelected.ID.Low
                myText = (oSelected.Text)
                oSelected.Text = UCase(myText)
                oSelected.Rewrite
                oSelected.Redraw
                
            ElseIf whataelement = msdElementTypeTextNode Then
                Dim oSelectedTLE As TextNodeElement
                Set oSelectedTLE = oEnumerator.Current
                ID = oSelectedTLE.ID.Low
                If Me.CheckBox2 Then
                    chkb2 = oSelectedTLE.TextLinesCount
                Else
                    chkb2 = 1
                End If
                For i = 1 To chkb2
                    myText = oSelectedTLE.TextLine(i)
                    oSelectedTLE.TextLine(i) = UCase(myText)
                    oSelectedTLE.Rewrite
                    oSelectedTLE.Redraw
                Next i
                
            Else
            
            End If
        
errorhandler:
            'nenechame se vycukat
        Loop
End Sub

Private Sub CommandButton4_Click()
        'all aaa
        Dim oEnumerator As ElementEnumerator
        Set oEnumerator = ActiveModelReference.GetSelectedElements
        Dim oSelected_whata As Element
        Dim myText As String
        
        Do While (oEnumerator.MoveNext)
            Set oSelected_whata = oEnumerator.Current
            Dim whataelement As MsdElementType
            whataelement = oSelected_whata.Type
            On Error GoTo errorhandler
            
            If whataelement = msdElementTypeText Then
                Dim oSelected As TextElement
                Set oSelected = oEnumerator.Current
                ID = oSelected.ID.Low
                myText = (oSelected.Text)
                oSelected.Text = LCase(myText)
                oSelected.Rewrite
                oSelected.Redraw
                
            ElseIf whataelement = msdElementTypeTextNode Then
                Dim oSelectedTLE As TextNodeElement
                Set oSelectedTLE = oEnumerator.Current
                ID = oSelectedTLE.ID.Low
                If Me.CheckBox2 Then
                    chkb2 = oSelectedTLE.TextLinesCount
                Else
                    chkb2 = 1
                End If
                For i = 1 To chkb2
                    myText = oSelectedTLE.TextLine(i)
                    oSelectedTLE.TextLine(i) = LCase(myText)
                    oSelectedTLE.Rewrite
                    oSelectedTLE.Redraw
                Next i
                
            Else
            
            End If
        
errorhandler:
            'nenechame se vycukat
        Loop
End Sub

Private Sub CommandButton5_Click()
   'all Aaaa
    Dim oEnumerator As ElementEnumerator
        Set oEnumerator = ActiveModelReference.GetSelectedElements
        Dim oSelected_whata As Element
        Dim myText As String
        
        Do While (oEnumerator.MoveNext)
            Set oSelected_whata = oEnumerator.Current
            Dim whataelement As MsdElementType
            whataelement = oSelected_whata.Type
            On Error GoTo errorhandler
            
            If whataelement = msdElementTypeText Then
                Dim oSelected As TextElement
                Set oSelected = oEnumerator.Current
                ID = oSelected.ID.Low
                myText = (oSelected.Text)
                oSelected.Text = UCase(Mid(myText, 1, 1)) & LCase(Mid(myText, 2, Len(myText)))
                oSelected.Rewrite
                oSelected.Redraw
                
            ElseIf whataelement = msdElementTypeTextNode Then
                Dim oSelectedTLE As TextNodeElement
                Set oSelectedTLE = oEnumerator.Current
                ID = oSelectedTLE.ID.Low
                If Me.CheckBox2 Then
                    chkb2 = oSelectedTLE.TextLinesCount
                Else
                    chkb2 = 1
                End If
                For i = 1 To chkb2
                    myText = oSelectedTLE.TextLine(i)
                    oSelectedTLE.TextLine(i) = UCase(Mid(myText, 1, 1)) & LCase(Mid(myText, 2, Len(myText)))
                    oSelectedTLE.Rewrite
                    oSelectedTLE.Redraw
                Next i
                
            Else
            
            End If
        
errorhandler:
            'nenechame se vycukat
        Loop
End Sub

Private Sub CommandButton6_Click()
        'divide text node to text line
        Dim oEnumerator As ElementEnumerator
        Set oEnumerator = ActiveModelReference.GetSelectedElements
        
        Do While (oEnumerator.MoveNext)
            Set oSelected_whata = oEnumerator.Current
            Dim whataelement As MsdElementType
            whataelement = oSelected_whata.Type
            On Error GoTo errorhandler
                
            If whataelement = msdElementTypeTextNode Then
                '
                Dim oSelectedTLE As TextNodeElement
                Set oSelectedTLE = oEnumerator.Current
                ID = oSelectedTLE.ID.Low
                Dim text_point As Point3d
                Dim text_rot As Matrix3d
                text_point = oSelectedTLE.Origin
                text_rot = oSelectedTLE.Rotation
                text_heigth = ActiveSettings.TextStyle.Height
                
                Dim oTe As TextElement
                
                For i = 1 To oSelectedTLE.TextLinesCount
                    text_point.Y = text_point.Y - CDbl(Replace(Me.TextBox5.Value, ".", ","))
                    If oSelectedTLE.TextLine(i) <> "" Then
                        Set oTe = CreateTextElement1(Nothing, oSelectedTLE.TextLine(i), text_point, text_rot)
                        ActiveModelReference.AddElement oTe
                        oTe.Redraw
                    End If
                Next i
                
                If Me.CheckBox4 Then oSelectedTLE.DeleteAllTextLines
                    
            End If
            
errorhandler:

        Loop
            
End Sub

Private Sub CommandButton7_Click()
    'overwrite
    Dim oEnumerator As ElementEnumerator
        Set oEnumerator = ActiveModelReference.GetSelectedElements
        Dim oSelected_whata As Element
        Dim myText As String
        
        Do While (oEnumerator.MoveNext)
            Set oSelected_whata = oEnumerator.Current
            Dim whataelement As MsdElementType
            whataelement = oSelected_whata.Type
            On Error GoTo errorhandler
            
            If whataelement = msdElementTypeText Then
                Dim oSelected As TextElement
                Set oSelected = oEnumerator.Current
                ID = oSelected.ID.Low
                
                oSelected.Text = Me.TextBox6
                oSelected.Rewrite
                oSelected.Redraw
                
            ElseIf whataelement = msdElementTypeTextNode Then
                Dim oSelectedTLE As TextNodeElement
                Set oSelectedTLE = oEnumerator.Current
                ID = oSelectedTLE.ID.Low
                If Me.CheckBox2 Then
                    chkb2 = oSelectedTLE.TextLinesCount
                Else
                    chkb2 = 1
                End If
                For i = 1 To chkb2
                    myText = oSelectedTLE.TextLine(i)
                    oSelectedTLE.TextLine(i) = Me.TextBox6
                    oSelectedTLE.Rewrite
                    oSelectedTLE.Redraw
                Next i
                
            Else
            
            End If
        
errorhandler:
            'nenechame se vycukat
        Loop
End Sub

Private Sub Label3_Click()
    Dim oEnumerator As ElementEnumerator
    Set oEnumerator = ActiveModelReference.GetSelectedElements
    
    Do While (oEnumerator.MoveNext)
            Set oSelected_whata = oEnumerator.Current
            Dim whataelement As MsdElementType
            whataelement = oSelected_whata.Type
            On Error GoTo errorhandler
                
            If whataelement = msdElementTypeTextNode Then
                '
                Dim oSelectedTLE As TextNodeElement
                Set oSelectedTLE = oEnumerator.Current
                ID = oSelectedTLE.ID.Low
                Me.TextBox5 = oSelectedTLE.LineSpacing + ActiveSettings.TextStyle.Height
                Exit Sub
            
            End If
            
errorhandler:

        Loop
End Sub
