Attribute VB_Name = "Class_ILoc"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements ILocateCommandEvents
Function ReadElement(oBase As Element, tInputPoint As Point3d, bAddToModel As Boolean) As Element

End Function
Private Sub ILocateCommandEvents_Accept(ByVal Element As Element, Point As Point3d, ByVal View As View)
    Call UserForm1.first_of_all(Element)
End Sub
Private Sub ILocateCommandEvents_Cleanup()

End Sub

Private Sub ILocateCommandEvents_Dynamics(Point As Point3d, ByVal View As View, ByVal DrawMode As MsdDrawingMode)
End Sub

Private Sub ILocateCommandEvents_LocateFailed()
    'CommandState.StartLocate New C_ILoc
    UserForm1.CommandButton2.Enabled = True
End Sub
Private Sub ILocateCommandEvents_LocateFilter(ByVal Element As Element, Point As Point3d, Accepted As Boolean)
End Sub

Private Sub ILocateCommandEvents_LocateReset()
    UserForm1.CommandButton2.Enabled = True
End Sub

Private Sub ILocateCommandEvents_Start()
    Dim lc As LocateCriteria
    Set lc = CommandState.CreateLocateCriteria(False)
    CommandState.SetLocateCriteria lc
    UserForm1.CommandButton2.Enabled = False


End Sub

Attribute VB_Name = "Module1"
Sub start_mte()
    UserForm1.SpinButton1.Value = UserForm1.Label9
    UserForm1.Show
End Sub

''''''''''''''
'Szabo Gabor '09
'MultiTextEditor v_04

Attribute VB_Name = "UserForm1"
Attribute VB_Base = "0{469A20B2-C2D0-4427-97F8-32730DBE69A4}{CAC147DE-9998-45BD-B331-049193D9E290}"
Attribute VB_GlobalNameSpace = False
Attribute VB_Creatable = False
Attribute VB_PredeclaredId = True
Attribute VB_Exposed = False
Attribute VB_TemplateDerived = False
Attribute VB_Customizable = False
Function read_text(ByVal text As MicroStationDGN.TextElement)
    read_text = text.text
End Function
Function read_textnode(ByVal text As MicroStationDGN.TextNodeElement, ByVal line As Integer)
    read_textnode text.TextLine(line)
End Function
Sub write_text(ByVal text As MicroStationDGN.TextElement)
    text.Rewrite
    text.Redraw
End Sub
Sub write_textnode(ByVal text As MicroStationDGN.TextNodeElement, ByVal line As Integer, ByVal newText As String)
    text.TextLine(line) = newText
    text.Rewrite
    text.Redraw
End Sub

Private Sub CommandButton1_Click()
    Dim oEnumerator As ElementEnumerator
    Set oEnumerator = ActiveModelReference.GetSelectedElements
    Do While (oEnumerator.MoveNext)
        Dim oSelected As MicroStationDGN.Element
        Set oSelected = oEnumerator.Current
        Call first_of_all(oSelected)
    Loop
End Sub

Sub make_your_job(ByVal oTE As TextElement)
        If UserForm1.TextBox1.Value <> "" Or UserForm1.TextBox2.Value <> "" Then
            'prefix appendix
            Call prefapp(oTE)
            'write
            Call write_text(oTE)
        End If
        If UserForm1.TextBox3.Value <> "" Or UserForm1.TextBox4.Value <> "" Then
            'replace
            Call replace_text(oTE)
            'write
            Call write_text(oTE)
        End If
        If UserForm1.OptionButton1.Value = True Or UserForm1.OptionButton2.Value = True Or UserForm1.OptionButton3.Value = True Then
            'change case
            Call case_change(oTE)
            'write
            Call write_text(oTE)
        End If
        If UserForm1.TextBox5.Value <> "" Then
            'overwrite
            Call overwrite(oTE)
            'write
            Call write_text(oTE)
        End If
        If CheckBox6.Value = True Then
            'underline
            Call underlinetext(oTE)
            'write
            Call write_text(oTE)
        End If
        If UserForm1.TextBox7.Value <> "" Then
            'scale
            Call scale_text(oTE)
            'write
            Call write_text(oTE)
        End If
        If UserForm1.TextBox8.Value <> "" Then
            'scale
            Call round_number(oTE)
            'write
            Call write_text(oTE)
        End If
        If UserForm1.TextBox9.Value <> "" Then
            'scale
            Call caluclate_text(oTE)
            'write
            Call write_text(oTE)
        End If
    End Sub
Sub first_of_all(ByVal oSelected As Element)

        If oSelected.Type = MsdElementType.msdElementTypeText Then
            'text
            Dim oTE As TextElement
            Set oTE = oSelected
            Call make_your_job(oTE)
        ElseIf oSelected.Type = MicroStationDGN.MsdElementType.msdElementTypeDimension Then
            If UserForm1.TextBox7.Value <> "" Then
'v8i                Dim oDi As DimensionElement
'                Dim oDiSt As DimensionStyle
'                Set oDi = oSelected
'                Set oDiSt = oDi.DimensionStyle
'                oDiSt.OverrideAnnotationScale = True
'                oDiSt.AnnotationScale = oDiSt.AnnotationScale * CDbl(Me.TextBox7.text)
'                oDi.DimensionStyle = oDiSt
'                oDi.Rewrite
'                oDi.Redraw
            End If
        ElseIf oSelected.Type = MicroStationDGN.MsdElementType.msdElementTypeTextNode Then
            Dim oTEN As TextNodeElement
            Dim oT As TextElement
            Set oTEN = oSelected
            Dim oTENsub As ElementEnumerator

            If Me.CheckBox2.Value = True Then
                Set oTENsub = oTEN.GetSubElements()
                Do While (oTENsub.MoveNext)
                    Set oT = oTENsub.Current
                    Call make_your_job(oT)
                Loop
            Else
                Set oTENsub = oTEN.GetSubElements()
                oTENsub.MoveNext
                Set oT = oTENsub.Current
                Call make_your_job(oT)
            End If

            If CheckBox4.Value = True Then
                'divide to text lines
                Dim text_point As Point3d
                Dim text_rot As Matrix3d
                Dim text_height As Long
                Dim i As Integer

                Set oTENsub = oTEN.GetSubElements()
                oTENsub.MoveNext
                Set oT = oTENsub.Current
                text_height = oT.TextStyle.Height

                Set oTEN = oSelected
                text_point = oTEN.Origin
                text_rot = oTEN.Rotation

                'find out the view rotational angle
                Dim angle As Double
                Matrix3dIsXYRotation ActiveDesignFile.Views.Item(Me.Label9).Rotation, angle

                For i = 1 To oTEN.TextLinesCount
 '                   Try
                     If Me.TextBox6.text <> "" Then
                        If Me.CheckBox7 = False Then
                        ' Divide normall
                        text_point.Y = text_point.Y - CDbl(Me.TextBox6.text)
                        Else
                        'divide by rot
                        text_point.X = text_point.X - Sin(angle) * CDbl(Me.TextBox6.text) / Sin(3.141592654 / 2 - angle)
                        text_point.Y = text_point.Y - CDbl(Me.TextBox6.text) '* Sin(angle)
                        End If
                        If oTEN.TextLine(i) <> "" Then
                            Set oT = CreateTextElement1(Nothing, oTEN.TextLine(i), text_point, text_rot)
                            ActiveModelReference.AddElement oT
                            oT.Redraw
                        End If
                    Else
'                    Catch ex As Exception
                        MsgBox "Please user number", , "MultiTextEditor"
                        GoTo aaa:
'                    End Try
                    End If
                Next i
aaa:
                If CheckBox5.Value = True Then
                    oTEN.DeleteAllTextLines
                End If
            End If

        ElseIf oSelected.Type = MicroStationDGN.MsdElementType.msdElementTypeCellHeader Then
            Dim oCellHeader As CellElement
            Set oCellHeader = oSelected
            Dim eleTemp As Element
            oCellHeader.ResetElementEnumeration

            Do While oCellHeader.MoveToNextElement(True)
                Set eleTemp = oCellHeader.CopyCurrentElement
                Dim fuckngtext As TextElement
                If eleTemp.IsTextNodeElement Then
                    Dim TNE As MicroStationDGN.TextNodeElement
                    Dim eleComponent As Element
                    Set TNE = eleTemp
                    Dim ee As ElementEnumerator
                    Dim counter As Integer
                    Set ee = TNE.GetSubElements
                    counter = 0
                    Do While (ee.MoveNext)

                        Set eleComponent = ee.Current
                        If eleComponent.IsTextElement Then
                            Set fuckngtext = eleComponent
                            Call make_your_job(fuckngtext)
                            counter = counter + 1
                        End If
                        If CheckBox2.Value = True = False And counter > 0 Then
                            GoTo endloop
                            'jinak to je svinstvo kamo
                        End If

                    Loop
endloop:
                ElseIf eleTemp.IsTextElement Then
                    fuckngtext = eleTemp
                    Call make_your_job(fuckngtext)
                End If
            Loop
        End If
End Sub

Private Sub Frame1_DblClick(ByVal Cancel As MSForms.ReturnBoolean)
    UserForm1.OptionButton1.Value = False
    UserForm1.OptionButton2.Value = False
    UserForm1.OptionButton3.Value = False
End Sub

Private Sub prefapp(ByRef text As TextElement)
        text.text = Me.TextBox1.text & text.text & Me.TextBox2.text
End Sub

Private Sub replace_text(ByRef text As TextElement)
        If CheckBox3.Value = True Then
            text.text = Replace(text.text, TextBox4.text, TextBox3.text, , , 0)
        Else
            text.text = Replace(text.text, TextBox4.text, TextBox3.text, , , 1)
        End If
End Sub
Private Sub case_change(ByRef text As TextElement)
    If UserForm1.OptionButton1 = True Then
        text.text = UCase(text.text)
    ElseIf UserForm1.OptionButton2 = True Then
        text.text = LCase(text.text)
    ElseIf UserForm1.OptionButton3 = True Then
        text.text = UCase(Mid(text.text, 1, 1)) & LCase(Mid(text.text, 2, Len(text.text)))
    End If
End Sub
Private Sub overwrite(ByRef text As TextElement)
    text.text = TextBox5.text
End Sub
Private Sub scale_text(ByVal text As TextElement)
    Dim tstyle As MicroStationDGN.TextStyle
    Set tstyle = text.TextStyle
    tstyle.Height = tstyle.Height * CDbl(Me.TextBox7.text)
    tstyle.Width = tstyle.Width * CDbl(Me.TextBox7.text)
End Sub
Private Sub underlinetext(ByRef text As TextElement)
    If text.TextStyle.IsUnderlined Then
        text.TextStyle.IsUnderlined = False
    Else
        text.TextStyle.IsUnderlined = True
    End If
End Sub
Private Sub round_number(ByRef text As TextElement)
    text.text = Replace(text.text, ".", ",")
    If IsNumeric(text.text) Then
        text.text = Round(text.text, CDbl(Me.TextBox8.Value))
    End If
    text.text = Replace(text.text, ",", ".")
End Sub
Private Sub caluclate_text(ByRef text As TextElement)
    text.text = Replace(text.text, ".", ",")
    If IsNumeric(text.text) Then
        text.text = CDbl(text.text) + CDbl(Me.TextBox9)
    End If
    text.text = Replace(text.text, ",", ".")
End Sub


Private Sub Label5_Click()
        Dim oEnumerator As ElementEnumerator
        Set oEnumerator = ActiveModelReference.GetSelectedElements
        Do While (oEnumerator.MoveNext)
            Dim oSelected As MicroStationDGN.Element
            Set oSelected = oEnumerator.Current
            If oSelected.Type = MicroStationDGN.MsdElementType.msdElementTypeTextNode Then
                Dim oTEN As MicroStationDGN.TextNodeElement
                Dim oT As MicroStationDGN.TextElement
                Dim oTENsub As MicroStationDGN.ElementEnumerator
                Set oTEN = oSelected
                Dim text_point As MicroStationDGN.Point3d
                Dim text_rot As MicroStationDGN.Matrix3d
                Dim text_height As Long

                Set oTENsub = oTEN.GetSubElements()
                oTENsub.MoveNext
                Set oT = oTENsub.Current
                text_height = oT.TextStyle.Height

                Set oTEN = oEnumerator.Current
                text_point = oTEN.Origin
                text_rot = oTEN.Rotation

                TextBox6.text = oTEN.LineSpacing + text_height
            End If
        Loop
    
End Sub

Private Sub CommandButton2_Click()
    CommandState.StartLocate New Class_ILoc
End Sub

Private Sub SpinButton1_Change()
    If SpinButton1.Value < 1 Then
        Me.SpinButton1.Value = 1
    End If
    If SpinButton1.Value > 8 Then
        Me.SpinButton1.Value = 8
    End If
    Me.Label9 = SpinButton1.Value
End Sub
