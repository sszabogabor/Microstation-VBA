Attribute VB_Name = "Module1"
Sub start_read_or_count()
    UserForm1.Show
End Sub

Sub whataelement()

    Dim oEnumerator As ElementEnumerator
        Dim oSelected As Element
        
        
        Set oEnumerator = ActiveModelReference.GetSelectedElements
        
        Do While (oEnumerator.MoveNext)
           
            Set oSelected = oEnumerator.Current
            Dim oType As MsdElementType
            oType = oSelected.Type
            
        Loop

End Sub


''''''''''''''
'Szabo Gabor '08

Attribute VB_Name = "UserForm1"
Attribute VB_Base = "0{72882B18-DD82-49C2-BEB5-4A671D4D893B}{70298830-3789-4D89-87A3-5AC2603D1DE6}"
Attribute VB_GlobalNameSpace = False
Attribute VB_Creatable = False
Attribute VB_PredeclaredId = True
Attribute VB_Exposed = False
Attribute VB_TemplateDerived = False
Attribute VB_Customizable = False

Private Sub CommandButton1_Click()
        
        Dim cislo As Double
        Dim oEnumerator As ElementEnumerator
        Set oEnumerator = ActiveModelReference.GetSelectedElements
        Dim oSelected_whata As Element
        
        If Me.OptionButton1 Then
            Do While (oEnumerator.MoveNext)
                Set oSelected_whata = oEnumerator.Current
                Dim whataelement As MsdElementType
                whataelement = oSelected_whata.Type
                On Error GoTo errorhandler
                
    
                    If whataelement = msdElementTypeText Then
                        Dim oSelected As TextElement
                        Set oSelected = oEnumerator.Current
                        ID = oSelected.ID.Low
                        ListBox1.AddItem (oSelected.Text)
        
                    ElseIf whataelement = msdElementTypeTextNode Then
                        Dim oSelectedTLE As TextNodeElement
                        Set oSelectedTLE = oEnumerator.Current
                        ID = oSelectedTLE.ID.Low
                        ListBox1.AddItem (oSelectedTLE.TextLine(1))
                    End If
                
            
errorhandler:
    
            Loop
        End If
        
    If Me.OptionButton2 Then
        Dim myArrays() As String
        Dim myCounts() As Integer
        
        ReDim myArrays(0) As String
        ReDim myCounts(0) As Integer
        Dim j As Integer
        j = 0
        Do While (oEnumerator.MoveNext)
                
                Set oSelected_whata = oEnumerator.Current
                Dim whataelement_ As MsdElementType
                whataelement_ = oSelected_whata.Type
                On Error GoTo errorhandler_

                    If whataelement_ = msdElementTypeText Then
                        Dim oSelected_ As TextElement
                        Dim nenaslesecislo As Boolean
                        Set oSelected_ = oEnumerator.Current
                        ID = oSelected_.ID.Low
                        
                        If j = 0 Then
                            myArrays(0) = oSelected_.Text
                            myCounts(0) = myCounts(i) + 1
                        Else

                        
                            For i = 0 To UBound(myArrays)
                                If myArrays(i) = oSelected_.Text Then
                                    myCounts(i) = myCounts(i) + 1
                                    nenaslesecislo = False
                                    Exit For
                                Else
                                    nenaslesecislo = True
                                End If
                            Next i
                                   
                                If nenaslesecislo Then
                                    ReDim Preserve myArrays(UBound(myArrays) + 1)
                                    ReDim Preserve myCounts(UBound(myCounts) + 1)
                                    myArrays(UBound(myArrays)) = oSelected_.Text
                                    myCounts(UBound(myCounts)) = myCounts(UBound(myCounts)) + 1
                                    
                                End If
                            
                        End If
                    j = j + 1

                    ElseIf whataelement_ = msdElementTypeTextNode Then
                    Dim oSelectedTLE_ As TextNodeElement
                    Set oSelectedTLE_ = oEnumerator.Current
                    ID = oSelectedTLE_.ID.Low

                        If j = 0 Then
                            myArrays(0) = oSelectedTLE_.TextLine(1)
                            myCounts(0) = myCounts(i) + 1
                        Else

                        
                            For i = 0 To UBound(myArrays)
                                If myArrays(i) = oSelectedTLE_.TextLine(1) Then
                                    myCounts(i) = myCounts(i) + 1
                                    nenaslesecislo = False
                                    Exit For
                                Else
                                    nenaslesecislo = True
                                End If
                            Next i
                                   
                                If nenaslesecislo Then
                                    ReDim Preserve myArrays(UBound(myArrays) + 1)
                                    ReDim Preserve myCounts(UBound(myCounts) + 1)
                                    myArrays(UBound(myArrays)) = oSelectedTLE_.TextLine(1)
                                    myCounts(UBound(myCounts)) = myCounts(UBound(myCounts)) + 1
                                    
                                End If
                            
                        End If
                    j = j + 1
                   End If

errorhandler_:

            Loop
    'vypis
        
        For i = 0 To UBound(myArrays)
            ListBox1.AddItem (myArrays(i) & "= " & myCounts(i) & "x")
        Next i

    End If
    

End Sub

Sub SortListBox(oLb As MSForms.ListBox)
    Dim vaItems As Variant
    Dim i As Long, j As Long
    Dim vTemp As Variant
   
    'Put the items in a variant array
    vaItems = oLb.List
   
    For i = LBound(vaItems, 1) To UBound(vaItems, 1) - 1
        For j = i + 1 To UBound(vaItems, 1)
            If vaItems(i, 0) > vaItems(j, 0) Then
                vTemp = vaItems(i, 0)
                vaItems(i, 0) = vaItems(j, 0)
                vaItems(j, 0) = vTemp
            End If
        Next j
    Next i
   
    'Clear the listbox
    oLb.Clear
   
    'Add the sorted array back to the listbox
    For i = LBound(vaItems, 1) To UBound(vaItems, 1)
        oLb.AddItem vaItems(i, 0)
    Next i
   
End Sub

Private Sub CommandButton2_Click()
    Me.ListBox1.Clear
End Sub

Private Sub CommandButton3_Click()
    Call Me.SortListBox(Me.ListBox1)
End Sub
