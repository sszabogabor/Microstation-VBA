Attribute VB_Name = "Module1"
Sub start_read_or_count()
    UserForm1.Show
End Sub

Sub whataelement()

    Dim oEnumerator As ElementEnumerator
        Dim oSelected As Element
        
        
        Set oEnumerator = ActiveModelReference.GetSelectedElements
        
        Do While (oEnumerator.MoveNext)
           
            Set oSelected = oEnumerator.Current
            Dim oType As MsdElementType
            oType = oSelected.Type
            
        Loop

End Sub


''''''''''''''
'Szabo Gabor '08

Attribute VB_Name = "UserForm1"
Attribute VB_Base = "0{0889A31B-F95A-4986-8D27-F77E07BF4DF3}{8DAB2BC3-5E07-4390-BAB2-F5965D94CCE2}"
Attribute VB_GlobalNameSpace = False
Attribute VB_Creatable = False
Attribute VB_PredeclaredId = True
Attribute VB_Exposed = False
Attribute VB_TemplateDerived = False
Attribute VB_Customizable = False
Public fake As Boolean
Private Sub CommandButton1_Click()
        
        Dim cislo As Double
        Dim oEnumerator As ElementEnumerator
        Set oEnumerator = ActiveModelReference.GetSelectedElements
        Dim oSelected_whata As Element
        
        If Me.OptionButton1 Then
            Do While (oEnumerator.MoveNext)
                Set oSelected_whata = oEnumerator.Current
                Dim whataelement As MsdElementType
                whataelement = oSelected_whata.Type
                On Error GoTo errorhandler
                Dim mytext() As String
     
                    If whataelement = msdElementTypeText Then
                        mytext() = FTextElement(oEnumerator.Current)
                        If mytext(0) <> " " Then
                            Me.ListBox1.AddItem (mytext(0))
                        End If
                    ElseIf whataelement = msdElementTypeTextNode Then
                        mytext() = FTextNodeElement(oEnumerator.Current)
                        For ii = 0 To UBound(mytext)
                            Me.ListBox1.AddItem (mytext(ii))
                        Next ii
                    ElseIf whataelement = msdElementTypeCellHeader Then
                        If Me.CheckBox1 Then
                            mytext() = FCellHeaderElem(oEnumerator.Current)
                            If fake = False Then
                                For ii = 0 To UBound(mytext)
                                    Me.ListBox1.AddItem (mytext(ii))
                                Next ii
                            End If
                        End If
                        
                    End If
                
            
errorhandler:
    
            Loop
        End If
        
    If Me.OptionButton2 Then
        Dim myArrays() As String
        Dim myCounts() As Integer
        
        ReDim myArrays(0) As String
        ReDim myCounts(0) As Integer
        Dim j As Integer
        j = 0
        Do While (oEnumerator.MoveNext)
                
                Set oSelected_whata = oEnumerator.Current
                Dim whataelement_ As MsdElementType
                whataelement_ = oSelected_whata.Type
                'On Error GoTo errorhandler_

                    If whataelement_ = msdElementTypeText Then
                        mytext() = FTextElement(oEnumerator.Current)
                        Call counter(mytext(), j, myArrays(), myCounts())
                    ElseIf whataelement_ = msdElementTypeTextNode Then
                        mytext() = FTextNodeElement(oEnumerator.Current)
                        Call counter(mytext(), j, myArrays(), myCounts())
                    ElseIf whataelement_ = msdElementTypeCellHeader Then
                        If Me.CheckBox1 Then
                            fake = False
                            mytext() = FCellHeaderElem(oEnumerator.Current)
                            If fake = False Then
                                Call counter(mytext(), j, myArrays(), myCounts())
                            End If
                        End If
                        
                    End If
                    
errorhandler_:

            Loop
     Call Me.output(myArrays(), myCounts())
    End If
    

End Sub

Sub SortListBox(oLb As MSForms.ListBox)
    Dim vaItems As Variant
    Dim i As Long, j As Long
    Dim vTemp As Variant
   
    'Put the items in a variant array
    vaItems = oLb.List
   
    For i = LBound(vaItems, 1) To UBound(vaItems, 1) - 1
        For j = i + 1 To UBound(vaItems, 1)
            If vaItems(i, 0) > vaItems(j, 0) Then
                vTemp = vaItems(i, 0)
                vaItems(i, 0) = vaItems(j, 0)
                vaItems(j, 0) = vTemp
            End If
        Next j
    Next i
   
    'Clear the listbox
    oLb.Clear
   
    'Add the sorted array back to the listbox
    For i = LBound(vaItems, 1) To UBound(vaItems, 1)
        oLb.AddItem vaItems(i, 0)
    Next i
   
End Sub

Private Sub CommandButton2_Click()
    Me.ListBox1.Clear
End Sub

Private Sub CommandButton3_Click()
    Call Me.SortListBox(Me.ListBox1)
End Sub

Function FTextElement(ByVal myelement As Element) As String()

    Dim oSelected As TextElement
    Set oSelected = myelement
    Dim textarray(0) As String
    textarray(0) = oSelected.Text
    FTextElement = textarray
    
End Function

Function FTextNodeElement(ByVal myelement As Element) As String()
    Dim oSelected As TextNodeElement
    Dim textarray() As String
    Set oSelected = myelement
    
    If Me.OptionButton3 Then
        ReDim textarray(0)
        textarray(0) = oSelected.TextLine(1)
        FTextNodeElement = textarray
    ElseIf Me.OptionButton4 Then
        ReDim textarray(0)
        For i = 1 To oSelected.TextLinesCount
            textarray(i - 1) = oSelected.TextLine(i)
            ReDim Preserve textarray(UBound(textarray) + 1)
        Next i
        ReDim Preserve textarray(UBound(textarray) - 1)
        FTextNodeElement = textarray
    ElseIf Me.OptionButton5 Then
        Dim allin1 As String
        ReDim textarray(0)
        For i = 1 To oSelected.TextLinesCount
            allin1 = allin1 & oSelected.TextLine(i) & " "
        Next i
        textarray(0) = allin1
        FTextNodeElement = textarray
    End If

End Function

Function FCellHeaderElem(ByVal myelement As Element) As String()
        Dim oCellHeader As CellElement
        Dim textarray() As String
        Dim TT As Boolean
        Dim TTN As Boolean
        Dim EEE As Boolean
        TT = False
        TTN = False
        EEE = False
        
        Set oCellHeader = myelement
        Set EE = oCellHeader.GetSubElements
            Dim eleComponent As Element
            Do While (EE.MoveNext)
                Set eleComponent = EE.Current
                    If eleComponent.Type = msdElementTypeText Then
                        textarray() = FTextElement(eleComponent)
                        FCellHeaderElem = textarray()
                        TT = True
                    ElseIf eleComponent.Type = msdElementTypeTextNode Then
                        textarray() = FTextNodeElement(eleComponent)
                        FCellHeaderElem = textarray()
                        TTN = True
                    Else
                        EEE = True
                    End If
            Loop
        If TT = False And TTN = False And EEE = True Then
            fake = True
        End If
End Function

Sub counter(ByRef mytext() As String, ByRef j As Integer, _
            ByRef myArrays() As String, ByRef myCounts() As Integer)
            
        On Error GoTo handler
        
        For ii = 0 To UBound(mytext)
        poslemetext = mytext(ii)
    
        If j = 0 Then
            myArrays(0) = poslemetext
            myCounts(0) = myCounts(i) + 1
        Else

        
            For i = 0 To UBound(myArrays)
                If myArrays(i) = poslemetext Then
                    myCounts(i) = myCounts(i) + 1
                    nenaslesecislo = False
                    Exit For
                Else
                    nenaslesecislo = True
                End If
            Next i
                   
                If nenaslesecislo Then
                    ReDim Preserve myArrays(UBound(myArrays) + 1)
                    ReDim Preserve myCounts(UBound(myCounts) + 1)
                    myArrays(UBound(myArrays)) = poslemetext
                    myCounts(UBound(myCounts)) = myCounts(UBound(myCounts)) + 1
                    
                End If
            
        End If
    j = j + 1
    Next ii
handler:
    On Error GoTo 0
End Sub

Sub output(ByRef myArrays() As String, ByRef myCounts() As Integer)

'vypis
        
        For i = 0 To UBound(myArrays)
            ListBox1.AddItem (myArrays(i) & "= " & myCounts(i) & "x")
        Next i

End Sub
