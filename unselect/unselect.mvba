Attribute VB_Name = "Module1"
Sub a()
    Set oEnumerator = ActiveModelReference.GetSelectedElements
            Do While (oEnumerator.MoveNext)
                Set oSelected_whata = oEnumerator.Current
                Set oModelRef = ActiveModelReference
                Dim whataelement As MsdElementType
                whataelement = oSelected_whata.Type
                
                
                    If whataelement = msdElementTypeLine Then
                        Set oSelected = oEnumerator.Current
                        If Not oSelected.Color = CInt(UserForm1.TextBox1.Text) Then
                            oModelRef.UnselectElement oSelected
                        End If
                    ElseIf whataelement = msdElementTypeTextNode Then
                        Set oSelected = oEnumerator.Current
                        If Not oSelected.Color = CInt(UserForm1.TextBox1.Text) Then
                            oModelRef.UnselectElement oSelected
                        End If
                    ElseIf whataelement = msdElementTypeTextNode Then
                        Set oSelected = oEnumerator.Current
                        If Not oSelected.Color = CInt(UserForm1.TextBox1.Text) Then
                            oModelRef.UnselectElement oSelected
                        End If
                    ElseIf whataelement = msdElementTypeDimension Then
                    Set oSelected = oEnumerator.Current
                        If Not oSelected.Color = CInt(UserForm1.TextBox1.Text) Then
                            oModelRef.UnselectElement oSelected
                        End If
                    ElseIf whataelement = msdElementTypeCellHeader Then
                    Set oSelected = oEnumerator.Current
                        If Not oSelected.Color = CInt(UserForm1.TextBox1.Text) Then
                            oModelRef.UnselectElement oSelected
                        End If
                    End If
            Loop

End Sub

Sub show()
    UserForm1.show
End Sub

Attribute VB_Name = "UserForm1"
Attribute VB_Base = "0{71CA2BB1-2A5C-4815-92A7-5B433A2213E9}{3603BFFF-AC0F-475B-9F47-C1CD83177288}"
Attribute VB_GlobalNameSpace = False
Attribute VB_Creatable = False
Attribute VB_PredeclaredId = True
Attribute VB_Exposed = False
Attribute VB_TemplateDerived = False
Attribute VB_Customizable = False
Private Sub CommandButton1_Click()
    
 Call Module1.a
End Sub
