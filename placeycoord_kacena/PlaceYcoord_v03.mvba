Attribute VB_Name = "Class1"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements IPrimitiveCommandEvents
Private a As Double

Private Sub IPrimitiveCommandEvents_DataPoint(Point As Point3d, ByVal View As View)
    
    Dim oTTStyle As TextStyle
    ActiveSettings.Level = ActiveDesignFile.Levels.FindByNumber(CInt(UserForm1.Label4))
    ActiveSettings.TextStyle = ActiveDesignFile.TextStyles.Find(UserForm1.ComboBox2.Text)
    Set oTTStyle = ActiveDesignFile.TextStyles.Find(UserForm1.ComboBox2.Text)
    'Dim myView As View
   'a = ActiveDesignFile.r
        
    ShowStatus "x: " & Point.X & " y: " & Point.Y & " z: " & Point.Z
    
    Dim oTe As TextElement
    Dim oM3DI As Matrix3d
    Dim oMatrix3d As Matrix3d
    'Dim dblRotAngle As Double
    'oMatrix3d = Matrix3dFromAxisAndRotationAngle(2, dblRotAngle)
    Dim tePoint As Point3d
    
     
    'text position about the horizontal line
    tePoint.X = Point.X
    
    If UserForm1.OptionButton2 Then
        If UserForm1.OptionButton3 Then
            tePoint.X = tePoint.X + oTTStyle.Height / 10
        ElseIf UserForm1.OptionButton4 Then
            tePoint.X = tePoint.X - oTTStyle.Height / 10
        End If
    End If
    If UserForm1.OptionButton1 Then
        tePoint.Y = Point.Y + 2 * (oTTStyle.Height * CDbl(Replace(UserForm1.TextBox6, ".", ","))) + (oTTStyle.Height * 1.5)
    ElseIf UserForm1.OptionButton2 Then
        If UserForm1.OptionButton5 = True Then
            'tePoint.Y = Point.Y - 3 * (oTTStyle.Height * CDbl(Replace(UserForm1.TextBox6, ".", ","))) + (oTTStyle.Height * 1.5)
            tePoint.Y = Point.Y - 3 * (oTTStyle.Height) + (oTTStyle.Height * 1.5)

        ElseIf UserForm1.OptionButton6 = True Then
            tePoint.Y = Point.Y - 2 * (oTTStyle.Height * CDbl(Replace(UserForm1.TextBox6, ".", ","))) - (oTTStyle.Height * 0.5)
        End If
    End If
    tePoint.Z = Point.Z
    
    'text justification
    If UserForm1.OptionButton3 Then
        ActiveSettings.TextStyle.Justification = msdTextJustificationLeftTop
    ElseIf UserForm1.OptionButton4 Then
        ActiveSettings.TextStyle.Justification = msdTextJustificationRightTop
    End If
    
    'pattern
    Dim patt As String
    patt = "0."
    For k = 0 To UserForm1.TextBox3.Value - 1
        patt = patt & "0"
    Next k
    If UserForm1.TextBox3.Value = 0 Then patt = "0"
    
    'create a text element
    Set oTe = CreateTextElement1(Nothing, UserForm1.TextBox4 & Format(Round(Point.Y, UserForm1.TextBox3.Value) _
                + Replace(UserForm1.TextBox2.Value, ".", ","), patt) & UserForm1.TextBox5, tePoint, oM3DI)
    ActiveModelReference.AddElement oTe
    oTe.Redraw
    
    'draw arrow
    Call Draw(Point, oTTStyle.Height, Abs(oTe.Boundary.Low.X - oTe.Boundary.High.X))
     
    
End Sub

' Reset event handler
Private Sub IPrimitiveCommandEvents_Reset()
    'prave tlacitko
    '  Clean up MicroStation's state and call
    '  IPrimitiveCommandEvents_Start again.
    CommandState.StartPrimitive Me
    
End Sub
Private Sub IPrimitiveCommandEvents_Start()
    CommandState.EnableAccuSnap
End Sub

Private Sub IPrimitiveCommandEvents_Keyin(ByVal Keyin As String)
    Debug.Print "keyin:" & Keyin
    ShowStatus "Keyin"
End Sub

Private Sub IPrimitiveCommandEvents_Cleanup()
    'ShowStatus "Cleanup"
    ShowPrompt "PlaceYcoord run, hit a point"
    'End
End Sub

Sub IPrimitiveCommandEvents_Dynamics(Point As Point3d, ByVal View As View, ByVal DrawMode As MsdDrawingMode)
    'Set DynaBlock = m_CARLDataBlock.Clone DynaBlock.Move Point DynaBlock.Redraw DrawMode
End Sub

Sub Draw(Point As Point3d, textheigth, textlength)
    a = textheigth * CDbl(Replace(UserForm1.TextBox6, ".", ","))
    'sipka
    Dim points(0 To 4) As Point3d
        
    points(0) = Point
    
    points(1).X = Point.X - a
    If UserForm1.OptionButton1 Then
        points(1).Y = Point.Y + a
    ElseIf UserForm1.OptionButton2 Then
        points(1).Y = Point.Y - a
    End If
    points(1).Z = Point.Z
    
    points(2).X = Point.X + a
    If UserForm1.OptionButton1 Then
        points(2).Y = Point.Y + a
    ElseIf UserForm1.OptionButton2 Then
        points(2).Y = Point.Y - a
    End If
    points(2).Z = Point.Z
    
    If UserForm1.OptionButton6 Then
        points(3).X = Point.X
        If UserForm1.OptionButton1 Then
            points(3).Y = Point.Y + 2 * a
        ElseIf UserForm1.OptionButton2 Then
            points(3).Y = Point.Y - 2 * a
        End If
        points(3).Z = Point.Z
        
        'points(4).X = Point.X + textlength
        If UserForm1.OptionButton3 Then
            points(4).X = Point.X + textlength
        ElseIf UserForm1.OptionButton4 Then
            points(4).X = Point.X - textlength
        End If
        If UserForm1.OptionButton1 Then
            points(4).Y = Point.Y + 2 * a
        ElseIf UserForm1.OptionButton2 Then
            points(4).Y = Point.Y - 2 * a
        End If
        points(4).Z = Point.Z
    End If
    
    If UserForm1.OptionButton5 Then
        points(3).X = Point.X
        If UserForm1.OptionButton1 Then
            points(3).Y = Point.Y + 2 * a / CDbl(Replace(UserForm1.TextBox6, ".", ","))
        ElseIf UserForm1.OptionButton2 Then
            points(3).Y = Point.Y - 3 * a / CDbl(Replace(UserForm1.TextBox6, ".", ","))
        End If
        points(3).Z = Point.Z
        
        'points(4).X = Point.X + textlength
        If UserForm1.OptionButton3 Then
            points(4).X = Point.X + textlength
        ElseIf UserForm1.OptionButton4 Then
            points(4).X = Point.X - textlength
        End If
        If UserForm1.OptionButton1 Then
            points(4).Y = Point.Y + 2 * a / CDbl(Replace(UserForm1.TextBox6, ".", ","))
        ElseIf UserForm1.OptionButton2 Then
            points(4).Y = Point.Y - 3 * a / CDbl(Replace(UserForm1.TextBox6, ".", ","))
        End If
        points(4).Z = Point.Z
    End If
    
    
    Dim oEl As LineElement
    Dim sestava_bodu(0 To 5) As Point3d
    sestava_bodu(0) = points(0)
    sestava_bodu(1) = points(2)
    sestava_bodu(2) = points(1)
    sestava_bodu(3) = points(0)
    sestava_bodu(4) = points(3)
    sestava_bodu(5) = points(4)
    
    ActiveSettings.Level = ActiveDesignFile.Levels.FindByNumber(CInt(UserForm1.Label4))
    Set oEl = CreateLineElement1(Nothing, sestava_bodu)
    ActiveModelReference.AddElement oEl
    oEl.Redraw
    
End Sub

Attribute VB_Name = "Class2"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements IPrimitiveCommandEvents
Private a As Double

Private Sub IPrimitiveCommandEvents_DataPoint(Point As Point3d, ByVal View As View)
    UserForm1.TextBox2.Text = Point.Y
End Sub

' Reset event handler
Private Sub IPrimitiveCommandEvents_Reset()
    'prave tlacitko
    '  Clean up MicroStation's state and call
    '  IPrimitiveCommandEvents_Start again.
    CommandState.StartPrimitive Me
    
End Sub
Private Sub IPrimitiveCommandEvents_Start()
    CommandState.EnableAccuSnap
End Sub

Private Sub IPrimitiveCommandEvents_Keyin(ByVal Keyin As String)

End Sub

Private Sub IPrimitiveCommandEvents_Cleanup()
    'ShowStatus "Cleanup"
   
    'End
End Sub

Sub IPrimitiveCommandEvents_Dynamics(Point As Point3d, ByVal View As View, ByVal DrawMode As MsdDrawingMode)
    'Set DynaBlock = m_CARLDataBlock.Clone DynaBlock.Move Point DynaBlock.Redraw DrawMode
End Sub

Attribute VB_Name = "Module1"
Sub PlaceYcoord()
    CommandState.StartPrimitive New Class1
    ShowPrompt "PlaceYcoord run, hit a point"
    UserForm1.Show
    
    'fill layers
    Dim oLevels As Levels
    Set oLevels = ActiveDesignFile.Levels
    
    For i = 1 To oLevels.Count
        UserForm1.ComboBox1.AddItem oLevels.Item(i).Name & "  #" & oLevels.Item(i).Number
    Next i
    
    'fill textstyles
    
    Dim oTStyles As TextStyles
    Set oTStyles = ActiveDesignFile.TextStyles
    
    For i = 1 To oTStyles.Count
        UserForm1.ComboBox2.AddItem oTStyles.Item(i).Name
    Next i
    
    UserForm1.ComboBox2.Value = ActiveSettings.TextStyle.Name
    
    
End Sub

Attribute VB_Name = "UserForm1"
Attribute VB_Base = "0{1683DA80-57A9-47C1-B9BD-5BAF8D4E96BE}{7A56D9C7-31ED-4AF2-BAEB-A93F2A642103}"
Attribute VB_GlobalNameSpace = False
Attribute VB_Creatable = False
Attribute VB_PredeclaredId = True
Attribute VB_Exposed = False
Attribute VB_TemplateDerived = False
Attribute VB_Customizable = False

Private Sub ComboBox1_Change()
    For i = 1 To Len(UserForm1.ComboBox1.Value)
        If Mid(UserForm1.ComboBox1.Value, i, 1) = "#" Then
            Exit For
        End If
    Next i
    UserForm1.Label4 = Mid(UserForm1.ComboBox1.Value, i + 1, Len(UserForm1.ComboBox1.Value))

End Sub



Private Sub CommandButton1_Click()
    CommandState.StartPrimitive New Class1
End Sub

Private Sub Label10_Click()
    '+selected
    Dim cislo As Double
        Dim oEnumerator As ElementEnumerator
        Set oEnumerator = ActiveModelReference.GetSelectedElements
        Dim oSelected_whata As Element
        Dim a As Double
        Dim b As Double
        
        Do While (oEnumerator.MoveNext)
            Set oSelected_whata = oEnumerator.Current
            Dim whataelement As MsdElementType
            whataelement = oSelected_whata.Type
            On Error GoTo errorhandler
            If whataelement = msdElementTypeText Then
                Dim oSelected As TextElement
                Set oSelected = oEnumerator.Current
                ID = oSelected.ID.Low
                a = CDbl(Replace((oSelected.Text), ".", ","))
            ElseIf whataelement = msdElementTypeTextNode Then
                Dim oSelectedTLE As TextNodeElement
                Set oSelectedTLE = oEnumerator.Current
                ID = oSelectedTLE.ID.Low
                a = CDbl(Replace((oSelectedTLE.TextLine(1)), ".", ","))
            ElseIf whataelement = msdElementTypeCellHeader Then
                Dim oSelectedCH As CellElement
                Set oSelectedCH = oEnumerator.Current
                ID = oSelectedCH.ID.Low
                'X = oSelectedCH.GetContainingNamedGroups
                'Y = oSelectedCH.
            End If
        Loop
errorhandler:
        b = CDbl(Replace(Me.TextBox2, ".", ","))
        Me.TextBox2 = a + b
        TextBox2 = Replace(TextBox2, ".", ",")
End Sub

Private Sub Label3_Click()
    '+y read ycoord and place to textbox
    CommandState.StartPrimitive New Class2
End Sub

Private Sub Label11_Click()
    a = TextBox2.Value
    TextBox2 = a * (-1)
    TextBox2 = Replace(TextBox2, ".", ",")
End Sub
