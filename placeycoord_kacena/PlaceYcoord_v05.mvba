Attribute VB_Name = "Class1"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements IPrimitiveCommandEvents
Private Sub IPrimitiveCommandEvents_DataPoint(Point As Point3d, ByVal View As View)
    'calculate distance
    Dim distance As Double
    Dim oEnumerator As ElementEnumerator
    Dim oSelected As Element
    Dim bline_ID As Double

    Set oEnumerator = ActiveModelReference.GetSelectedElements
    
    If ActiveModelReference.AnyElementsSelected = False Then
        ShowPrompt "PlaceYcoord run, Select Baseline!!"
        'Call IPrimitiveCommandEvents_Reset
        GoTo endsub
    End If
    
    Do While (oEnumerator.MoveNext)
       
        Set oSelected = oEnumerator.Current
        Dim oType As MsdElementType
        oType = oSelected.Type
        
        If oSelected.IsVertexList Then
        ' get vertices
        bline_ID = oSelected.ID.Low
        vertices = oSelected.AsVertexList.GetVertices
        Dim baseline_length As Double
        Dim a_length As Double
        Dim b_length As Double
        Dim angle_b As Double
'            vertices(0).X
'            vertices(0).Y
'            vertices(1).X
'            vertices(1).Y
        baseline_length = (((vertices(0).x - vertices(1).x)) ^ 2 + ((vertices(0).Y - vertices(1).Y)) ^ 2) ^ 0.5
        a_length = (((Point.x - vertices(1).x)) ^ 2 + ((Point.Y - vertices(1).Y)) ^ 2) ^ 0.5
        b_length = (((vertices(0).x - Point.x)) ^ 2 + ((vertices(0).Y - Point.Y)) ^ 2) ^ 0.5
        angle_b = ArcCos((baseline_length ^ 2 + a_length ^ 2 - b_length ^ 2) / (2 * baseline_length * a_length))
        distance = Sin(angle_b) * a_length
        End If

    Loop
    
    
    'create symbol
    
    Dim oTTStyle As TextStyle
    ActiveSettings.Level = ActiveDesignFile.Levels.FindByNumber(CInt(UserForm1.Label4))
    ActiveSettings.TextStyle = ActiveDesignFile.TextStyles.Find(UserForm1.ComboBox2.Text)
    Set oTTStyle = ActiveDesignFile.TextStyles.Find(UserForm1.ComboBox2.Text)
    'Dim myView As View
   'a = ActiveDesignFile.r
        
    ShowStatus "x: " & Point.x & " y: " & Point.Y & " z: " & Point.Z
    
    Dim oTe As TextElement
    Dim oM3DI As Matrix3d
    Dim oMatrix3d As Matrix3d
    'Dim dblRotAngle As Double
    'oMatrix3d = Matrix3dFromAxisAndRotationAngle(2, dblRotAngle)
    Dim tePoint As Point3d
    
     
    'text position about the horizontal line
    tePoint.x = Point.x
    
    If UserForm1.OptionButton2 Then
        If UserForm1.OptionButton3 Then
            tePoint.x = tePoint.x + oTTStyle.Height / 10
        ElseIf UserForm1.OptionButton4 Then
            tePoint.x = tePoint.x - oTTStyle.Height / 10
        End If
    End If
    If UserForm1.OptionButton1 Then
        tePoint.Y = Point.Y + 2 * (oTTStyle.Height * CDbl(Replace(UserForm1.TextBox6, ".", ","))) + (oTTStyle.Height * 1.5)
    ElseIf UserForm1.OptionButton2 Then
        If UserForm1.OptionButton5 = True Then
            'tePoint.Y = Point.Y - 3 * (oTTStyle.Height * CDbl(Replace(UserForm1.TextBox6, ".", ","))) + (oTTStyle.Height * 1.5)
            tePoint.Y = Point.Y - 3 * (oTTStyle.Height) + (oTTStyle.Height * 1.5)

        ElseIf UserForm1.OptionButton6 = True Then
            tePoint.Y = Point.Y - 2 * (oTTStyle.Height * CDbl(Replace(UserForm1.TextBox6, ".", ","))) - (oTTStyle.Height * 0.5)
        End If
    End If
    tePoint.Z = Point.Z
    
    'text justification
    If UserForm1.OptionButton3 Then
        ActiveSettings.TextStyle.Justification = msdTextJustificationLeftTop
    ElseIf UserForm1.OptionButton4 Then
        ActiveSettings.TextStyle.Justification = msdTextJustificationRightTop
    End If
    
    'pattern
    Dim patt As String
    patt = "0."
    For k = 0 To UserForm1.TextBox3.Value - 1
        patt = patt & "0"
    Next k
    If UserForm1.TextBox3.Value = 0 Then patt = "0"
    
    'create a text element
    'Set oTe = CreateTextElement1(Nothing, UserForm1.TextBox4 & Format(Round(Point.Y, UserForm1.TextBox3.Value) _
                + Replace(UserForm1.TextBox2.Value, ".", ","), patt) & UserForm1.TextBox5, tePoint, oM3DI)
    Set oTe = CreateTextElement1(Nothing, UserForm1.TextBox4 & Format(Round(distance * CInt(UserForm1.TextBox6.Value), UserForm1.TextBox3.Value) _
                + Replace(UserForm1.TextBox2.Value, ".", ","), patt) & UserForm1.TextBox5, tePoint, oM3DI)
    ActiveModelReference.AddElement oTe
    oTe.Redraw
    
    ActiveModelReference.SelectElement oTe
    Call Me.transform_rot(bline_ID, Point, ArcSin((Abs((vertices(0).Y - vertices(1).Y))) / baseline_length))
    
    'draw arrow
    Call Draw(Point, oTTStyle.Height, Abs(oTe.Boundary.Low.x - oTe.Boundary.High.x), bline_ID, ArcSin((Abs((vertices(0).Y - vertices(1).Y))) / baseline_length))

endsub:
    
End Sub

' Reset event handler
Private Sub IPrimitiveCommandEvents_Reset()
    'prave tlacitko
    '  Clean up MicroStation's state and call
    '  IPrimitiveCommandEvents_Start again.
    CommandState.StartPrimitive Me
    
End Sub
Private Sub IPrimitiveCommandEvents_Start()
    CommandState.EnableAccuSnap
End Sub

Private Sub IPrimitiveCommandEvents_Keyin(ByVal Keyin As String)
    Debug.Print "keyin:" & Keyin
    ShowStatus "Keyin"
End Sub

Private Sub IPrimitiveCommandEvents_Cleanup()
    'ShowStatus "Cleanup"
    ShowPrompt "PlaceYcoord run, hit a point"
    'End
End Sub

Sub IPrimitiveCommandEvents_Dynamics(Point As Point3d, ByVal View As View, ByVal DrawMode As MsdDrawingMode)
    'Set DynaBlock = m_CARLDataBlock.Clone DynaBlock.Move Point DynaBlock.Redraw DrawMode
End Sub

Sub Draw(Point As Point3d, textheigth, textlength, bline_ID As Double, angle_1 As Double)
    A = textheigth * CDbl(Replace(UserForm1.TextBox6, ".", ","))
    'sipka
    Dim points(0 To 4) As Point3d
    Dim bline_id_copy As Double
    bline_id_copy = bline_ID
        
    points(0) = Point
    
    points(1).x = Point.x - A
    If UserForm1.OptionButton1 Then
        points(1).Y = Point.Y + A
    ElseIf UserForm1.OptionButton2 Then
        points(1).Y = Point.Y - A
    End If
    points(1).Z = Point.Z
    
    points(2).x = Point.x + A
    If UserForm1.OptionButton1 Then
        points(2).Y = Point.Y + A
    ElseIf UserForm1.OptionButton2 Then
        points(2).Y = Point.Y - A
    End If
    points(2).Z = Point.Z
    
    If UserForm1.OptionButton6 Then
        points(3).x = Point.x
        If UserForm1.OptionButton1 Then
            points(3).Y = Point.Y + 2 * A
        ElseIf UserForm1.OptionButton2 Then
            points(3).Y = Point.Y - 2 * A
        End If
        points(3).Z = Point.Z
        
        'points(4).X = Point.X + textlength
        If UserForm1.OptionButton3 Then
            points(4).x = Point.x + textlength
        ElseIf UserForm1.OptionButton4 Then
            points(4).x = Point.x - textlength
        End If
        If UserForm1.OptionButton1 Then
            points(4).Y = Point.Y + 2 * A
        ElseIf UserForm1.OptionButton2 Then
            points(4).Y = Point.Y - 2 * A
        End If
        points(4).Z = Point.Z
    End If
    
    If UserForm1.OptionButton5 Then
        points(3).x = Point.x
        If UserForm1.OptionButton1 Then
            points(3).Y = Point.Y + 2 * A / CDbl(Replace(UserForm1.TextBox6, ".", ","))
        ElseIf UserForm1.OptionButton2 Then
            points(3).Y = Point.Y - 3 * A / CDbl(Replace(UserForm1.TextBox6, ".", ","))
        End If
        points(3).Z = Point.Z
        
        'points(4).X = Point.X + textlength
        If UserForm1.OptionButton3 Then
            points(4).x = Point.x + textlength
        ElseIf UserForm1.OptionButton4 Then
            points(4).x = Point.x - textlength
        End If
        If UserForm1.OptionButton1 Then
            points(4).Y = Point.Y + 2 * A / CDbl(Replace(UserForm1.TextBox6, ".", ","))
        ElseIf UserForm1.OptionButton2 Then
            points(4).Y = Point.Y - 3 * A / CDbl(Replace(UserForm1.TextBox6, ".", ","))
        End If
        points(4).Z = Point.Z
    End If
    
    
    Dim oEl As LineElement
    Dim sestava_bodu(0 To 5) As Point3d
    sestava_bodu(0) = points(0)
    sestava_bodu(1) = points(2)
    sestava_bodu(2) = points(1)
    sestava_bodu(3) = points(0)
    sestava_bodu(4) = points(3)
    sestava_bodu(5) = points(4)
    
    ActiveSettings.Level = ActiveDesignFile.Levels.FindByNumber(CInt(UserForm1.Label4))
    Set oEl = CreateLineElement1(Nothing, sestava_bodu)
    ActiveModelReference.AddElement oEl
    oEl.Redraw
    
    ActiveModelReference.SelectElement oEl
    Call Me.transform_rot(bline_id_copy, Point, angle_1)
    
End Sub

Public Function ArcCos(A As Double) As Double
   
  'Inverse Cosine

    On Error Resume Next

        If A = 1 Then
            ArcCos = 0
            Exit Function
        End If

        ArcCos = Atn(-A / Sqr(-A * A + 1)) + 2 * Atn(1)
    On Error GoTo 0

End Function

Public Function ArcSin(x As Double) As Double

  'Inverse Sine

    On Error Resume Next
        ArcSin = Atn(x / Sqr(-x * x + 1))
    On Error GoTo 0

End Function

Public Function transform_rot(ByRef bline_ID As Double, ByRef pointaboutrot As Point3d, angle_by_baseline As Double)

    'find out the view rotational angle
        Dim angle As Double
        Matrix3dIsXYRotation ActiveDesignFile.Views.Item(UserForm1.Label14).Rotation, angle
    'rotate selection set
        Dim RotationMatrix As Matrix3d
        Dim Eltrans As Transform3d
        Dim pointAbout As Point3d
        pointAbout = pointaboutrot
        '  Create a rotation matrix for rotating with the Z direction fixed.
        Dim Axis As Point3d
        Axis.x = 0
        Axis.Y = 0
        Axis.Z = 1
        If UserForm1.OptionButton7.Value = True Then
            RotationMatrix = Matrix3dFromVectorAndRotationAngle(Axis, -angle)
        ElseIf UserForm1.OptionButton8.Value = True Then
            RotationMatrix = Matrix3dFromVectorAndRotationAngle(Axis, angle_by_baseline)
        End If
        
        Eltrans = Transform3dFromMatrix3dAndFixedPoint3d(RotationMatrix, pointAbout)
    
        Dim oEnumerator As ElementEnumerator
        Set oEnumerator = ActiveModelReference.GetSelectedElements
        Dim oElement As Element
        
        Do While oEnumerator.MoveNext
            Set oElement = oEnumerator.Current
            '  Apply the transform to rotate the element
            If oElement.ID.Low <> bline_ID Then
           
                oElement.transform Eltrans
                oElement.Rewrite
                oElement.Redraw
                ActiveModelReference.UnselectElement oElement
            End If
        Loop

End Function

Attribute VB_Name = "Module1"
Sub PlaceYcoord()
    CommandState.StartPrimitive New Class1
    ShowPrompt "PlaceYcoord run, hit a point"
    UserForm1.Show
    
    'fill layers
    Dim oLevels As Levels
    Set oLevels = ActiveDesignFile.Levels
    
    For i = 1 To oLevels.Count
        UserForm1.ComboBox1.AddItem oLevels.Item(i).Name & "  #" & oLevels.Item(i).Number
    Next i
    'fill textstyles
    
    Dim oTStyles As TextStyles
    Set oTStyles = ActiveDesignFile.TextStyles
    
    For i = 1 To oTStyles.Count
        UserForm1.ComboBox2.AddItem oTStyles.Item(i).Name
    Next i
    
    UserForm1.ComboBox2.Value = ActiveSettings.TextStyle.Name
    
    
End Sub

Attribute VB_Name = "UserForm1"
Attribute VB_Base = "0{59371CD5-C156-4997-B21E-1BA45214E7A7}{C5D82E87-3D4A-40CC-B164-1385E282BABC}"
Attribute VB_GlobalNameSpace = False
Attribute VB_Creatable = False
Attribute VB_PredeclaredId = True
Attribute VB_Exposed = False
Attribute VB_TemplateDerived = False
Attribute VB_Customizable = False
Private Sub ComboBox1_Change()
    For i = 1 To Len(UserForm1.ComboBox1.Value)
        If Mid(UserForm1.ComboBox1.Value, i, 1) = "#" Then
            Exit For
        End If
    Next i
    UserForm1.Label4 = Mid(UserForm1.ComboBox1.Value, i + 1, Len(UserForm1.ComboBox1.Value))

End Sub

Private Sub CommandButton1_Click()
    CommandState.StartPrimitive New Class1
End Sub

Private Sub Label10_Click()
    '+selected
    Dim cislo As Double
        Dim oEnumerator As ElementEnumerator
        Set oEnumerator = ActiveModelReference.GetSelectedElements
        Dim oSelected_whata As Element
        Dim A As Double
        Dim b As Double
        
        Do While (oEnumerator.MoveNext)
            Set oSelected_whata = oEnumerator.Current
            Dim whataelement As MsdElementType
            whataelement = oSelected_whata.Type
            On Error GoTo errorhandler
            If whataelement = msdElementTypeText Then
                Dim oSelected As TextElement
                Set oSelected = oEnumerator.Current
                A = CDbl(Replace((oSelected.Text), ".", ","))
            ElseIf whataelement = msdElementTypeTextNode Then
                Dim oSelectedTLE As TextNodeElement
                Set oSelectedTLE = oEnumerator.Current
                A = CDbl(Replace((oSelectedTLE.TextLine(1)), ".", ","))
            ElseIf whataelement = msdElementTypeCellHeader Then
                Dim oCellHeader As CellElement
                Set oCellHeader = oEnumerator.Current
                Set ee = oCellHeader.GetSubElements
                    Dim eleComponent As Element
                    Do While (ee.MoveNext)
                        Set eleComponent = ee.Current
                            If eleComponent.Type = msdElementTypeText Then
                                Dim oSelected1 As TextElement
                                Set oSelected1 = ee.Current
                                cislo = CDbl(oSelected1.Text)
                                A = CDbl(Replace((cislo), ".", ","))
                            ElseIf eleComponent.Type = msdElementTypeTextNode Then
                                Dim oTNE1 As TextNodeElement
                                Set oTNE1 = eleComponent
                                'Set oSelectedTLE = oEnumerator.Current
                                'ID = oSelectedTLE.ID.Low
                                cislo = CDbl(oTNE1.TextLine(1))
                                A = CDbl(Replace((cislo), ".", ","))
                            End If
                    Loop
            End If
        Loop
errorhandler:
        b = CDbl(Replace(Me.TextBox2, ".", ","))
        Me.TextBox2 = A + b
        TextBox2 = Replace(TextBox2, ".", ",")
End Sub


Private Sub Label11_Click()
    A = TextBox2.Value
    TextBox2 = A * (-1)
    TextBox2 = Replace(TextBox2, ".", ",")


Private Sub SpinButton1_Change()
    If SpinButton1.Value < 1 Then
        Me.SpinButton1.Value = 1
    End If
    If SpinButton1.Value > 8 Then
        Me.SpinButton1.Value = 8
    End If
    Me.Label14 = SpinButton1.Value
End Sub
