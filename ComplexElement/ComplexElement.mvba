Attribute VB_Name = "Module1"

Sub a()
    Dim cislo As Double
        Dim oEnumerator As ElementEnumerator
        Set oEnumerator = ActiveModelReference.GetSelectedElements
        Dim eleComponent As Element
        Dim oSelected As ComplexElement
        
        Do While (oEnumerator.MoveNext)
            Set oSelected = oEnumerator.Current
            Set ee = oSelected.GetSubElements
    
            Do While (ee.MoveNext)
                Set eleComponent = ee.Current
                MsgBox eleComponent.Type
            Loop

        Loop
        
End Sub
