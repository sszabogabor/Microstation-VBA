Attribute VB_Name = "Module2"
Sub PlaceLine()
    CommandState.StartPrimitive New clsPlaceLineCommand
End Sub

Attribute VB_Name = "clsPlaceLineCommand"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements IPrimitiveCommandEvents

Private m_atPoints(0 To 1) As Point3d
Private m_at_cara_Points(0 To 1) As Point3d
Private m_nPoints As Integer

Private Sub IPrimitiveCommandEvents_Cleanup()

End Sub

Private Sub IPrimitiveCommandEvents_DataPoint(Point As Point3d, ByVal View As View)
    
    'CadInputQueue.SendKeyin "PLACE NOTE ICON "
    
    If m_nPoints = 0 Then
        CommandState.StartDynamics
        m_atPoints(0) = Point
        m_nPoints = 1
        ShowPrompt "Place end point"
    ElseIf m_nPoints = 1 Then
        m_atPoints(1) = Point
        Dim oEl As LineElement
        Set oEl = CreateLineElement1(Nothing, m_atPoints)
        ActiveModelReference.AddElement oEl
        oEl.Redraw
        m_atPoints(0) = m_atPoints(1)
           
        
        'vodorovna cara
        m_at_cara_Points(0) = m_atPoints(0)
        m_at_cara_Points(1).X = m_atPoints(1).X + 1
        m_at_cara_Points(1).Y = m_atPoints(1).Y
        Set oEl = CreateLineElement1(Nothing, m_at_cara_Points)
        ActiveModelReference.AddElement oEl
        oEl.Redraw
        
        
        End
    End If

End Sub


Private Sub IPrimitiveCommandEvents_Dynamics(Point As Point3d, ByVal View As View, ByVal DrawMode As MsdDrawingMode)
    If m_nPoints = 1 Then
        m_atPoints(1) = Point
        Dim oEl As LineElement
        Set oEl = CreateLineElement1(Nothing, m_atPoints)
        oEl.Redraw DrawMode
    End If
End Sub

Private Sub IPrimitiveCommandEvents_Keyin(ByVal Keyin As String)

End Sub

Private Sub IPrimitiveCommandEvents_Reset()
    CommandState.StartPrimitive Me
    m_nPoints = 0
End Sub

Private Sub IPrimitiveCommandEvents_Start()
    ShowCommand "VBA PlaceLine Example"
    ShowPrompt "Select start of line"
End Sub
