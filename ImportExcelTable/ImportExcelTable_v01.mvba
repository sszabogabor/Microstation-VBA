Attribute VB_Name = "Class1"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements IPrimitiveCommandEvents
Private a As Double

Private Sub IPrimitiveCommandEvents_DataPoint(point As Point3d, ByVal View As View)
    ShowStatus "x: " & point.X & " y: " & point.Y & " z: " & point.Z

    'draw table
    Call UserForm1.draw(point) ', Abs(oTe.Boundary.Low.X - oTe.Boundary.High.X))
    
End Sub

' Reset event handler
Private Sub IPrimitiveCommandEvents_Reset()
    'prave tlacitko
    '  Clean up MicroStation's state and call
    '  IPrimitiveCommandEvents_Start again.
    CommandState.StartPrimitive Me
    
End Sub
Private Sub IPrimitiveCommandEvents_Start()
    CommandState.EnableAccuSnap
End Sub

Private Sub IPrimitiveCommandEvents_Keyin(ByVal Keyin As String)
'    Debug.Print "keyin:" & Keyin
'    ShowStatus "Keyin"
End Sub

Private Sub IPrimitiveCommandEvents_Cleanup()
    'ShowStatus "Cleanup"
'    ShowPrompt "PlaceYcoord run, hit a point"
    'End
End Sub

Sub IPrimitiveCommandEvents_Dynamics(point As Point3d, ByVal View As View, ByVal DrawMode As MsdDrawingMode)
    'Set DynaBlock = m_CARLDataBlock.Clone DynaBlock.Move Point DynaBlock.Redraw DrawMode
End Sub

Attribute VB_Name = "Module1"
Sub start_importexceltable()
    Call load_textstyles
    Call load_excel_workbooks
    Call load_layers
    UserForm1.Show
    
End Sub

Sub load_excel_workbooks()
    Dim w As Excel.Workbook
    Dim excelApp As Excel.Application
    Set excelApp = GetObject(, "Excel.Application")
    
    UserForm1.ComboBox1.Clear
    For Each w In excelApp.Workbooks
        UserForm1.ComboBox1.AddItem (w.Name)
    Next
    
End Sub

Sub load_textstyles()
    Dim textst As TextStyle
    UserForm1.ComboBox3.Clear
    For Each textst In Application.ActiveDesignFile.TextStyles
        UserForm1.ComboBox3.AddItem (textst.Name)
    Next
    
    UserForm1.ComboBox3.Value = MicroStationDGN.ActiveSettings.TextStyle.Name
    
End Sub

Sub load_layers()
    Dim lev As Level
    UserForm1.ComboBox4.Clear
    For Each lev In Application.ActiveDesignFile.Levels
        UserForm1.ComboBox4.AddItem (lev.Name)
    Next
    UserForm1.ComboBox4.Value = MicroStationDGN.ActiveSettings.Level.Name
End Sub

Attribute VB_Name = "UserForm1"
Attribute VB_Base = "0{16019204-FB87-4811-9D64-75DFEFAB6FCD}{E40A8B28-6792-43C8-8E4C-D25B41E6E2ED}"
Attribute VB_GlobalNameSpace = False
Attribute VB_Creatable = False
Attribute VB_PredeclaredId = True
Attribute VB_Exposed = False
Attribute VB_TemplateDerived = False
Attribute VB_Customizable = False
Dim excelApp As Excel.Application

Private Sub ComboBox1_Change()
    Set excelApp = GetObject(, "Excel.Application")
    UserForm1.ComboBox2.Clear
    If UserForm1.ComboBox1.Value = "" Then
        MsgBox "Please chose workbook", , "8)"
    Else
        excelApp.Workbooks(UserForm1.ComboBox1.Value).Activate
        Label2 = excelApp.ActiveWorkbook.Path & "\" & excelApp.ActiveWorkbook.Name
    End If
    
    Dim mysheets As Excel.Worksheet
    For Each mysheets In excelApp.ActiveWorkbook.Worksheets
        UserForm1.ComboBox2.AddItem (mysheets.Name)
    Next
End Sub

Private Sub ComboBox2_Change()
    excelApp.Worksheets(UserForm1.ComboBox2.Value).Activate
End Sub

Private Sub CommandButton1_Click()
    CommandState.StartPrimitive New Class1
End Sub

Sub draw(point)
        'read data
    Dim data() As String
        'set settings
        
    ActiveSettings.TextStyle = ActiveDesignFile.TextStyles.Find(UserForm1.ComboBox3.Text)
    ActiveSettings.Level = ActiveDesignFile.Levels.Find(UserForm1.ComboBox4.Text)

    sel_row = excelApp.Selection.Row
    sel_column = excelApp.Selection.Column
    sel_rows = excelApp.Selection.Rows.Count
    sel_columns = excelApp.Selection.Columns.Count
    
    ReDim Preserve data(sel_rows - 1, sel_columns - 1)
    
    For i = 0 To sel_rows - 1
        For j = 0 To sel_columns - 1
            data(i, j) = excelApp.Cells(sel_row + i, sel_column + j)
        Next j
    Next i
    
    'read column width
    Dim column_width() As Double
    Dim row_height() As Double
    ReDim column_width(sel_columns - 1)
    ReDim row_height(sel_rows - 1)
    
    For i = 0 To sel_columns - 1
        column_width(i) = excelApp.Columns(sel_column + i).ColumnWidth * 7.456 * CDbl(UserForm1.TextBox1)
    Next i
    
    For i = 0 To sel_rows - 1
        row_height(i) = excelApp.Rows(sel_row + i).RowHeight * CDbl(UserForm1.TextBox1)
    Next i
        
    Dim points(0 To 1) As Point3d
    Dim b_points(0 To 1) As Point3d
    Dim oEl As LineElement
    Dim oM3DI As Matrix3d
    b_points(0) = point
    b_points(1) = point
    points(0) = point
    points(1) = point
    
    Dim oTe As TextElement
    Dim tePoint As Point3d
    Dim lines() As LineElement
    
    l = 0

    
    'find border, make table
    
    For i = sel_column To sel_column + sel_columns - 1
        b_points(0).Y = point.Y
        b_points(1).Y = point.Y
    
        If l = 0 Then
            b_points(0).X = b_points(0).X
            b_points(1).X = b_points(0).X + column_width(i - sel_column) / 1000
        Else
            b_points(0).X = b_points(1).X
            b_points(1).X = b_points(1).X + column_width(i - sel_column) / 1000
        End If

        For j = sel_row To sel_row + sel_rows - 1
            borET = excelApp.Cells(j, i).Borders(xlEdgeTop).LineStyle
            borEB = excelApp.Cells(j, i).Borders(xlEdgeBottom).LineStyle
            borEL = excelApp.Cells(j, i).Borders(xlEdgeLeft).LineStyle
            borER = excelApp.Cells(j, i).Borders(xlEdgeRight).LineStyle
            'find text justifikation in cells
            alignm = excelApp.Cells(j, i).HorizontalAlignment
            Select Case alignm
                Case 1
                    'nothing
                    cell_justif = 0.5
                    ActiveSettings.TextStyle.Justification = MicroStationDGN.msdTextJustificationCenterCenter
                Case -4108
                    'center
                    cell_justif = 0.5
                    ActiveSettings.TextStyle.Justification = MicroStationDGN.msdTextJustificationCenterCenter
                Case -4131
                    'left
                    cell_justif = 0.05
                    ActiveSettings.TextStyle.Justification = MicroStationDGN.msdTextJustificationLeftCenter
                Case -4152
                    'right
                    cell_justif = 0.95
                    ActiveSettings.TextStyle.Justification = MicroStationDGN.msdTextJustificationRightCenter
            End Select
            

            If l = 0 Then
                b_points(0).Y = b_points(0).Y
                b_points(1).Y = b_points(0).Y - row_height(j - sel_row) / 1000
            Else
                b_points(0).Y = b_points(1).Y
                b_points(1).Y = b_points(1).Y - row_height(j - sel_row) / 1000
            End If
            l = l + 1
            
'            points(0).X = b_points(0).X
'            points(0).Y = b_points(0).Y
'            points(1).X = b_points(1).X
'            points(1).Y = b_points(0).Y
'            points(2).X = b_points(1).X
'            points(2).Y = b_points(1).Y
'            points(3).X = b_points(0).X
'            points(3).Y = b_points(1).Y
                       
            
            If borET > 0 Then
                points(0).X = b_points(0).X
                points(0).Y = b_points(0).Y
                points(1).X = b_points(1).X
                points(1).Y = b_points(0).Y
                Set oEl = CreateLineElement1(Nothing, points)
                ActiveModelReference.AddElement oEl
                oEl.Redraw
'                ReDim Preserve lines(UBound(lines) + 1)
'                Set lines(UBound(lines)) = oEl
            End If
            If borEB > 0 Then
                points(0).X = b_points(1).X
                points(0).Y = b_points(1).Y
                points(1).X = b_points(0).X
                points(1).Y = b_points(1).Y
                Set oEl = CreateLineElement1(Nothing, points)
                ActiveModelReference.AddElement oEl
                oEl.Redraw
'                ReDim Preserve lines(UBound(lines) + 1)
'                Set lines(UBound(lines)) = oEl
            End If
            If borEL > 0 Then
                points(0).X = b_points(0).X
                points(0).Y = b_points(0).Y
                points(1).X = b_points(0).X
                points(1).Y = b_points(1).Y
                Set oEl = CreateLineElement1(Nothing, points)
                ActiveModelReference.AddElement oEl
                oEl.Redraw
'                ReDim Preserve lines(UBound(lines) + 1)
'                Set lines(UBound(lines)) = oEl
            End If
            If borER > 0 Then
                points(0).X = b_points(1).X
                points(0).Y = b_points(0).Y
                points(1).X = b_points(1).X
                points(1).Y = b_points(1).Y
                Set oEl = CreateLineElement1(Nothing, points)
                ActiveModelReference.AddElement oEl
                oEl.Redraw
'                ReDim Preserve lines(UBound(lines) + 1)
'                Set lines(UBound(lines)) = oEl
            End If
'            write text
            tePoint.X = b_points(0).X + cell_justif * column_width(i - sel_column) / 1000
            tePoint.Y = b_points(0).Y - 0.5 * row_height(j - sel_row) / 1000
            Set oTe = CreateTextElement1(Nothing, data(j - sel_row, i - sel_column), tePoint, oM3DI)
            ActiveModelReference.AddElement oTe
            oTe.Redraw
            
        Next j
    Next i
    
'  'find out elements for deleting -  duplicated lines
'  Dim line_index_todel() As Integer
'  For i = 0 To sel_rows * sel_columns
'    For j = i + 1 To sel_rows * sel_columns
'        If lines(i).StartPoint.X = lines(j).StartPoint.X And lines(i).EndPoint.X = lines(j).EndPoint.X _
'        And lines(i).StartPoint.Y = lines(j).StartPoint.Y And lines(i).EndPoint.Y = lines(j).EndPoint.Y Then
'            ReDim Preserve line_index_todel(UBound(line_index_todel) + 1)
'            line_index_todel(UBound(line_index_todel)) = i
'        End If
'    Next j
'  Next i
    
End Sub
