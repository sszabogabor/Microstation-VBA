Attribute VB_Name = "Class1"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements ILocateCommandEvents

Private Sub ILocateCommandEvents_Accept(ByVal Element As Element, Point As Point3d, ByVal View As View)
    Call UserForm1.make(Element)
    CommandState.StartLocate New Class1
End Sub

Private Sub ILocateCommandEvents_Cleanup()

End Sub

Private Sub ILocateCommandEvents_Dynamics(Point As Point3d, ByVal View As View, ByVal DrawMode As MsdDrawingMode)
End Sub

Private Sub ILocateCommandEvents_LocateFailed()
    CommandState.StartLocate New Class1
End Sub

Private Sub ILocateCommandEvents_LocateFilter(ByVal Element As Element, Point As Point3d, Accepted As Boolean)

End Sub

Private Sub ILocateCommandEvents_LocateReset()

End Sub

Private Sub ILocateCommandEvents_Start()
    Dim lc As LocateCriteria
    Set lc = CommandState.CreateLocateCriteria(False)
    CommandState.SetLocateCriteria lc
End Sub

Attribute VB_Name = "Module1"
Sub TextDimChanger()
    'fill textstyles
    Dim oTStyles As TextStyles
    Set oTStyles = ActiveDesignFile.TextStyles
    For i = 1 To oTStyles.Count
        UserForm1.ComboBox1.AddItem oTStyles.Item(i).Name
    Next i
    'set current style
    UserForm1.ComboBox1.Value = ActiveSettings.TextStyle.Name
    
    'fill dimstyles
    Dim oDStyles As DimensionStyles
    Set oDStyles = ActiveDesignFile.DimensionStyles
    For i = 1 To oDStyles.Count
        UserForm1.ComboBox2.AddItem oDStyles.Item(i).Name
    Next i
    'set dimstyle
    UserForm1.ComboBox2.Value = ActiveSettings.DimensionStyle.Name
    
    UserForm1.Show
End Sub

Attribute VB_Name = "UserForm1"
Attribute VB_Base = "0{248BE27F-B2FD-4505-B52B-0DA3C95CDE1D}{360EC120-4E83-4293-8D16-C200F96308C7}"
Attribute VB_GlobalNameSpace = False
Attribute VB_Creatable = False
Attribute VB_PredeclaredId = True
Attribute VB_Exposed = False
Attribute VB_TemplateDerived = False
Attribute VB_Customizable = False
Private Sub CommandButton1_Click()
    Dim oEnumerator As ElementEnumerator
    Set oEnumerator = ActiveModelReference.GetSelectedElements
    Do While (oEnumerator.MoveNext)
       Call make(oEnumerator.Current)
    Loop
End Sub

Sub a_text(ByRef a As Element)
    Dim oTTStyle As TextStyle
    Set oTTStyle = ActiveDesignFile.TextStyles.Find(UserForm1.ComboBox1.Text)
    Set a.AsTextElement.TextStyle = oTTStyle
    a.Redraw
    a.Rewrite
End Sub

Sub a_dimelement(ByRef a As Element)
    Dim oDStyle As DimensionStyle
    Set oDStyle = ActiveDesignFile.DimensionStyles.Find(UserForm1.ComboBox2.Text)
    Set a.AsDimensionElement.DimensionStyle = oDStyle
    a.Redraw
    a.Rewrite
End Sub

Private Sub CommandButton2_Click()
    CommandState.StartLocate New Class1
End Sub

Sub make(ByRef oElement As MicroStationDGN.Element)
   
    If oElement.Type = msdElementTypeText Then
            Call a_text(oElement)
    ElseIf oElement.Type = msdElementTypeDimension Then
            Call Me.a_dimelement(oElement)
    ElseIf oElement.Type = msdElementTypeCellHeader Then
            Dim oCellHeader As CellElement
            Set oCellHeader = oElement
            Set ee = oCellHeader.GetSubElements
                Dim eleComponent As Element
                Do While (ee.MoveNext)
                    Set eleComponent = ee.Current
                        If eleComponent.Type = msdElementTypeText Then
                            Call a_text(eleComponent)
                        ElseIf eleComponent.Type = msdElementTypeTextNode Then
                            Dim oTNE As TextNodeElement
                            Set oTNE = eleComponent
                            Set ee1 = oTNE.GetSubElements
                                    Do While (ee1.MoveNext)
                                        Call a_text(ee1.Current)
                                    Loop
                        
                        End If
                Loop
    
    
    End If
End Sub
