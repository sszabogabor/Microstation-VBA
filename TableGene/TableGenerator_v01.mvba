Attribute VB_Name = "Class1"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements IPrimitiveCommandEvents
Private a As Double

Private Sub IPrimitiveCommandEvents_DataPoint(point As Point3d, ByVal View As View)
    
    Dim oTTStyle As TextStyle
    'ActiveSettings.Level = ActiveDesignFile.Levels.Find(UserForm1.ComboBox2.Text)
    ActiveSettings.TextStyle = ActiveDesignFile.TextStyles.Find(UserForm1.ComboBox1.Text)
    Set oTTStyle = ActiveDesignFile.TextStyles.Find(UserForm1.ComboBox1.Text)
        
    ShowStatus "x: " & point.X & " y: " & point.Y & " z: " & point.Z

    'draw table
    Call Draw(point, oTTStyle.Height) ', Abs(oTe.Boundary.Low.X - oTe.Boundary.High.X))
    Call Write_(point)
    
End Sub

' Reset event handler
Private Sub IPrimitiveCommandEvents_Reset()
    'prave tlacitko
    '  Clean up MicroStation's state and call
    '  IPrimitiveCommandEvents_Start again.
    CommandState.StartPrimitive Me
    
End Sub
Private Sub IPrimitiveCommandEvents_Start()
    CommandState.EnableAccuSnap
End Sub

Private Sub IPrimitiveCommandEvents_Keyin(ByVal Keyin As String)
    Debug.Print "keyin:" & Keyin
    ShowStatus "Keyin"
End Sub

Private Sub IPrimitiveCommandEvents_Cleanup()
    'ShowStatus "Cleanup"
    ShowPrompt "PlaceYcoord run, hit a point"
    'End
End Sub

Sub IPrimitiveCommandEvents_Dynamics(point As Point3d, ByVal View As View, ByVal DrawMode As MsdDrawingMode)
    'Set DynaBlock = m_CARLDataBlock.Clone DynaBlock.Move Point DynaBlock.Redraw DrawMode
End Sub

Sub Draw(point As Point3d, textheigth) ', textlength)
     'nastavim hladinu
    ActiveSettings.Level = ActiveDesignFile.Levels.Find(UserForm1.ComboBox2.Text)
    Dim a As Double

    'a = textheigth * CDbl(Replace(UserForm1.TextBox1, ".", ","))
    a = textheigth * UserForm1.TextBox1.Value
    'sipka
   
    Dim points(0 To 1) As Point3d
    Dim oEl As LineElement
    points(0) = point
    points(1) = point

    points(1).X = point.X + a * CDbl(Replace(UserForm1.TextBox2, ".", ",")) * CDbl(Replace(UserForm1.TextBox4, ".", ",")) / UserForm1.TextBox1.Value
    
    'horizontal
    For i = 0 To CInt(Replace(UserForm1.TextBox3, ".", ","))
        points(0).Y = point.Y - a * i
        points(1).Y = point.Y - a * i
        
        Set oEl = CreateLineElement1(Nothing, points)
        ActiveModelReference.AddElement oEl
        oEl.Redraw
    
    Next i
    
    points(0) = point
    points(1) = point

    points(1).Y = point.Y - a * CDbl(Replace(UserForm1.TextBox3, ".", ","))
    'vertical
    For i = 0 To CInt(Replace(UserForm1.TextBox2, ".", ","))
        points(0).X = point.X + a * i * CDbl(Replace(UserForm1.TextBox4, ".", ",")) / UserForm1.TextBox1.Value
        points(1).X = point.X + a * i * CDbl(Replace(UserForm1.TextBox4, ".", ",")) / UserForm1.TextBox1.Value

        Set oEl = CreateLineElement1(Nothing, points)
        ActiveModelReference.AddElement oEl
        oEl.Redraw

    Next i

    
End Sub

Sub Write_(point As Point3d)
    Dim oTe As TextElement
    Dim tePoint As Point3d
    Dim oM3DI As Matrix3d

    ActiveSettings.TextStyle = ActiveDesignFile.TextStyles.Find(UserForm1.ComboBox1.Text)
    ActiveSettings.TextStyle.Justification = msdTextJustificationCenterCenter
    Set oTTStyle = ActiveDesignFile.TextStyles.Find(UserForm1.ComboBox1.Text)
    a = oTTStyle.Height
    For j = 0 To CInt(Replace(UserForm1.TextBox3, ".", ",")) - 1
        For i = 0 To CInt(Replace(UserForm1.TextBox2, ".", ",")) - 1
            tePoint = point
            tePoint.X = point.X + a * UserForm1.TextBox4.Value / 2 + i * a * UserForm1.TextBox4.Value
            tePoint.Y = point.Y - a * UserForm1.TextBox1.Value / 2 - j * a * UserForm1.TextBox1.Value
            Set oTe = CreateTextElement1(Nothing, "0", tePoint, oM3DI)
            ActiveModelReference.AddElement oTe
            oTe.Redraw
        Next i
    Next j
    
End Sub

Attribute VB_Name = "Module1"
Sub Tablegene()
    'CommandState.StartPrimitive New Class1
    ShowPrompt "Hit a base point"

    UserForm1.Show
    
    'fill layers
    Dim oLevels As Levels
    Set oLevels = ActiveDesignFile.Levels
    
    For i = 1 To oLevels.Count
        UserForm1.ComboBox2.AddItem oLevels.Item(i).Name '  & "  #" & oLevels.Item(i).Number
    Next i
    UserForm1.ComboBox2.Value = ActiveSettings.Level.Name
    
    'fill textstyles
    
    Dim oTStyles As TextStyles
    Set oTStyles = ActiveDesignFile.TextStyles
    
    For i = 1 To oTStyles.Count
        UserForm1.ComboBox1.AddItem oTStyles.Item(i).Name
    Next i
    
    UserForm1.ComboBox1.Value = ActiveSettings.TextStyle.Name

End Sub

Attribute VB_Name = "UserForm1"
Attribute VB_Base = "0{9141E773-A40F-46B6-9131-9D7416F4671D}{CF068D98-5D0E-4AF0-BA88-8C93570919B0}"
Attribute VB_GlobalNameSpace = False
Attribute VB_Creatable = False
Attribute VB_PredeclaredId = True
Attribute VB_Exposed = False
Attribute VB_TemplateDerived = False
Attribute VB_Customizable = False
Private Sub ComboBox1_Change()
    ActiveSettings.TextStyle = ActiveDesignFile.TextStyles.Find(UserForm1.ComboBox1.Text)
End Sub

Private Sub ComboBox2_Change()
    ActiveSettings.Level = ActiveDesignFile.Levels.Find(UserForm1.ComboBox2.Text)
End Sub

Private Sub CommandButton1_Click()
    CommandState.StartPrimitive New Class1
End Sub
